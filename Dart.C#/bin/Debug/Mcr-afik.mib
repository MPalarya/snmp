--
-- ELBIT-GLOBAL-REG-V2.mib
-- MIB generated by MG-SOFT Visual MIB Builder 2013 (32-bit) Version 9.0  Build 720
-- Monday, August 24, 2015 at 09:18:44
--

--  ELBIT-GLOBAL-REG.mib
-- 
-- 

	ELBIT-GLOBAL-REG-V2 DEFINITIONS ::= BEGIN
 
		IMPORTS
			enterprises			
				FROM RFC1155-SMI			
			Integer32, OBJECT-TYPE, NOTIFICATION-TYPE			
				FROM SNMPv2-SMI;
	
	
--
-- Type definitions
--
	
		TypeVswrOkNotOk ::= INTEGER
			{
			vswrOk(1),
			vswrNotOk(2)
			}

		TypeSynthesizrLock ::= INTEGER
			{
			synthIsUnLock(1),
			synthIsLock(2)
			}

		TypeShortLong ::= INTEGER
			{
			short(1),
			long(2)
			}

		TypeFrequency ::= INTEGER (4400000..5000000)
-- Frequency values range
		TypeGrcMode ::= INTEGER
			{
			ptp(1),
			mpt2p(2),
			sp1(3),
			sp2(4)
			}
-- ptp   - Point to point
-- mpt2p - Multpoint to 2 point
-- sp1   - Single point 1
-- sp2   - Single point 2

			
-- Carrier working bitmap
		TypeCarrierBitmapMode ::= INTEGER (0..63)


		TypeTxLevel ::= INTEGER
			{
			txlevelOFF(1),
			txLevelLow(2),
			txLevelHigh(3),
			txLevelAuto(4),
			txLevelManual(5)
			}
-- When working with TXlevelMaual then oduMenualPower is the trasmition power level
		TypePowerLevel ::= INTEGER (11..40)
-- The manual power level can be in range 11 -40 db
		TypeModem ::= INTEGER
			{
			modem64QAM(1),
			modem16QAM(2),
			modemQPSK(3)
			}
-- Transmit and receive modulation type
-- Link modem bit rate
		TypeLinkBitRate ::= INTEGER
			{
			linkrate1024KBs(1),
			linkrate2048KBs(2),
			linkrate4096KBs(3),
			linkrate8448KBs(4),
			linkrate16MBs(5),
			linkrate34MBs(6),
			linkrate52MBs(7),
			linkrate104MBs(8)
			}

		TypeOnOff ::= INTEGER
			{
			offState(1),
			onState(2)
			}
-- To on off prarameters 
		TypeUpLoadMode ::= INTEGER
			{
			singleParametr(1),
			pageParametr(2),
			pageTest(3),
			pageLoadToHw(4)
			}
-- This option enables the Magaer to upload paraamters in single parametr mode and multiparameters mode at once.
-- In case of working in single parametr mode each parameter is set to Hw after it's leagal check.
-- In case of working in page parameters only range of values is tests and after change this OID to pageTest or to pageLoadToHw than all parameters are test at once.
-- In case of conflict in one of parameters then the error should be apear in OID oduPageSetupStatus that is in status
		TypeIfModemOffset ::= INTEGER (0..127)
-- If modem offset from is origin value
		TypeBandSelect ::= INTEGER
			{
			band1(1),
			band2(2),
			band3(3),
			band4(4)
			}
			                            
			
		TypeBand ::= INTEGER
		{
		   band1(0),
		   band2(1),
		   band3(2),
		   band4(3)
		}
		TypeModemLock ::= INTEGER
			{
			modemUnLock(1),
			modemLock(2)
			}

		TypeStatusuploadCheck ::= INTEGER
			{
			setupOk(1),
			rfFrequency(2),
			txModem(3),
			rxModem(4),
			rfip(5),
			txlinkbitratemp(6),
			rxlinkbitratemp(7),
			txlevelautompt2p(8),
			notPointToPoint(9),
			txfreqclose(10),
			rxfreqclose(11)
			}
-- Possible error List for Page mode only
		TypeTestLoop ::= INTEGER
			{
			loopOFF(1),
			loopBack(2),
			loopBB1(3),
			loopBB2(4),
			loopRF(5)
			}
-- Loops possibilities
-- Select Channel to activate - only the write option has meaning - wich channel number you want to activate
		TypeSelectChannel ::= INTEGER
			{
			selectChannel1(1),
			selectChannel2(2),
			selectChannel3(3),
			selectChannel4(4),
			selectChannel5(5),
			selectChannel6(6),
			selectChannel7(7),
			selectChannel8(8),
			selectChannel9(9),
			selectChannel10(10)
			}

		TypeModemAction ::= INTEGER
			{
			singlebyteRead(1),
			singlebytereadWrite(3),
			multybyteRead(5),
			multybyteWrite(6)
			}
			
-- For APC handeling (automatic Transmit power level magement)
		TypeDeltaPower ::= INTEGER (-100..100)

-- Maximum Power to Transmit
		TypeMaxPower ::= INTEGER (1..37)

-- Minimum Rssi Level in Dbm
		TypeRssiValue ::= INTEGER (-100..-10)

-- Modem Prefec Errors
		TypePrefecBer ::= OCTET STRING (SIZE (0..255))

		TypeFpgaRegAddress ::= INTEGER (0..65535)

		TypeFpgaRegValue ::= INTEGER (0..255)

		TypeScanningElevation ::= INTEGER (0..10)

		TypeAzimithscanning ::= INTEGER (0..60)

		TypeBandNum ::= INTEGER
			{
			twoband(2),
			fourband(4)
			}

		TypeHopFixMode ::= INTEGER
			{
			fixmode(1),
			hopmode(2)
			}

		TypehopRate ::= INTEGER
			{
			qpskRate3(1),
			qam16Rate3(2),
			qam64Rate3(3),
			qpskRate2(4),
			qam16Rate2(5),
			qam64Rate2(6)
			}
-- Discribes the hop diffrent Rates
-- rateQPSKrate3     - 2.8Mbps  (QPSK,  R=1/3)
-- rateQPSKrate2     - 4.17Mbps (QPSK,  R=1/2)
-- rate16QAMrate3    - 5.6Mbps  (16QAM, R=1/3)
-- rate16QAMrate2    - 8.37Mbps (16QAM, R=1/2)
-- rate64QAMrate3    - 8.48Mbps (64QAM, R=1/3)
-- rate64QAMrate2    - 12.5Mbps (64QAM, R=1/2)
-- 
-- 
		TypeAgcWorkingMode ::= INTEGER
			{
			agcManual(1),
			agcAutomatic(2)
			}

		TypeMesureSrc ::= INTEGER
			{
			mesureFromBaseBand(1),
			mesureFromIf(2)
			}

		TypeAttenToUse ::= INTEGER
			{
			useAttVVA(1),
			useAttDCA(2)
			}

		TypeLnaOnOff ::= INTEGER
			{
			lnaOFF(1),
			lnaON(2)
			}

		TypeRssMesureOnOFF ::= INTEGER
			{
			rssiMESOFF(1),
			rssiMESON(2)
			}

		TypeStepSize ::= INTEGER
			{
			plusMinus1(1),
			tBD(2)
			}

		TypeATenuatorCtrlSelect ::= INTEGER
			{
			hwCtrl(1),
			swCtrl(2)
			}

		TypeChannelOn ::= INTEGER
			{
			channelOFF(0),
			channelON(1)
			}

		TypePowerMode ::= INTEGER
			{
			chipRun(0),
			fullPowerDown(1),
			standBy(2),
			reset(3)
			}

		TypeDisableEnable ::= INTEGER
			{
			disable(1),
			enable(2)
			}

		TypeRfSyntClkPower ::= INTEGER
			{
			disableRfSynt(0),
			min9Dbm(1),
			min6Dbm(2),
			min3Dbm(3),
			zeroDbm(4),
			threeDbm(7)
			}

		TypeDCAAtt ::= INTEGER (0..63)

		TypeLoopSet ::= INTEGER
			{
			mormalOperation(0),
			test(1)
			}

		TypePathMode ::= INTEGER
			{
			fixAttPath(0),
			varAttandGainPath(1)
			}

		TypeMixerGain ::= INTEGER
			{
			nominal(0),
			minus6Db(1)
			}

		TypeScanninSpeed ::= INTEGER
			{
			lowestSpeed(1),
			lowSpeed(2),
			lowestHighSpeed(3),
			highSpeed(4)
			}
-- Scanning Speeds
-- 
-- 1 - Lowest Speed
-- 2 - Low Speed
-- 3 - Lowest High Speed
-- 4 - High Speed
		TypeCoarseDAC ::= INTEGER (0..15)

		TypeDacWork ::= INTEGER
			{
			dacWorks(0),
			dacSleep(1)
			}

		TypeInitAzimuthScan ::= INTEGER
			{
			azLeft(1),
			azRight(2)
			}

		TypeFifoValue ::= INTEGER (0..15)

		TypeFifoInValue ::= INTEGER (0..3 | 8..11)

		TypeDataFormator ::= INTEGER
			{
			frame(0),
			sync(1),
			noSync(2)
			}

		TypeDivderSelect ::= INTEGER
			{
			ostr(0),
			frameorSync(1)
			}

		TypeChargePump ::= INTEGER
			{
			noChargePump(0),
			singleChargePump(1),
			dualChargePump(2)
			}

		TypeCfgStartRegister ::= INTEGER
			{
			clearAllPorts(0),
			cfgAllAfe(1),
			cfgA2D(2),
			cfgD2A(4),
			cfgClkDstrb(8),
			cfgIduDCAAtt(16),
			cfgRxDCAAtt(32),
			cfgOCXOFreq(64)
			}

		TypeHopFreqTableSelect ::= INTEGER
			{
			table8MAll(1),
			table9MAll(2),
			table8M1A3(3),
			table8M2A4(4),
			table9M1A3(5),
			table9M2A4(6),
			table12MAll(7),
			table12M1A3(8),
			table12M2A4(9),
			table33MAll(10),
			table33MB(11)
			}

		TypeNumberOfFrequencies ::= INTEGER
			{
			oneFrequency(1),
			twoFrequencies(2),
			threeFrequencies(3),
			fourFrequencies(4),
			fiveFrequencies(5),
			sixFrequencies(6),
			sevenFrequencies(7),
			eightFrequencies(8)
			}

		TypePs10vOnOFF ::= INTEGER
			{
			ps10VON(1),
			ps10VOFF(2)
			}

		TypePowerAmpONOFF ::= INTEGER
			{
			powerAmpOFF(1),
			powerAmpON(2)
			}

		TypeManualMode ::= INTEGER
			{
			autoModeSelect(1),
			manualModeSelect(2)
			}

		TypeApcMode ::= INTEGER
			{
			noAPCMode(1),
			aPCMode(2)
			}

		TypeRssiMesureState ::= INTEGER
			{
			noRssiMesure(1),
			statrtRssiMesure(2)
			}

		TypeNumberOfBands ::= INTEGER
			{
			oneBand(1),
			twoBands(2),
			threeBands(3),
			fourBands(4)
			}

		TypeCommandExecutionStatus ::= INTEGER
			{
			idleState(1),
			executingState(2),
			abortState(3),
			queudState(4),
			faultState(5)
			}
-- Command Execution Status
-- 
-- 1 - Idle 
-- 2 - Executing
-- 3 - Abort
-- 4 - Queued
-- 5 - Fault
		TypeNumberofSubBands ::= INTEGER
			{
			oneBand(1),
			twoBands(2)
			}

		TypeFactorMulOrDiv ::= INTEGER
			{
			multplyFactor(1),
			divideFactor(2)
			}

		TypeNumberOfFrequenciesInBand ::= INTEGER (1..32)

		TypeFrequencyMember ::= INTEGER (1..32)

		TypeLinkId ::= INTEGER (1..511)

		TypeHopFrequencyKeySelect ::= INTEGER
			{
			selectKey1(1),
			selectKey2(2),
			selectKey3(3),
			selectKey4(4),
			selectKey5(5),
			selectKey6(6),
			selectKey7(7),
			selectKey8(8)
			}
-- Select Hop Frequency keySelect
		TypeDCAValue ::= INTEGER
			{
			gain0Db(0),
			gain0dot5Db(5),
			gain1Db(10),
			gain1Dot5Db(15),
			gain2Db(20),
			gain2Dot5Db(25),
			gain3Db(30),
			gain3Dot5Db(35),
			gain4Db(40),
			gain4Dot5Db(45),
			gain5Db(50),
			gain5Dot5Db(55),
			gain6Db(60),
			gain6Dot5Db(65),
			gain7Db(70),
			gain7Dot5Db(75),
			gain8Db(80),
			gain8Dot5Db(85),
			gain9Db(90),
			gain9Dot5Db(95),
			gain10Db(100),
			gain10Dot5Db(105),
			gain11Db(110),
			gain11Dot5Db(115),
			gain12Db(120),
			gain12Dot5Db(125),
			gain13Db(130),
			gain13Dot5Db(135),
			gain14Db(140),
			gain14Dot5Db(145),
			gain15Db(150),
			gain15Dot5Db(155),
			gain16Db(160),
			gain16Dot5Db(165),
			gain17Db(170),
			gain17Dot5Db(175),
			gain18Db(180),
			gain18Dot5Db(185),
			gain19Db(190),
			gain19Dot5Db(195),
			gain20Db(200),
			gain20Dot5Db(205),
			gain21Db(210),
			gain21Dot5Db(215),
			gain22Db(220),
			gain22Dot5Db(225),
			gain23Db(230),
			gain23Dot5Db(235),
			gain24Db(240),
			gain24Dot5Db(245),
			gain25Db(250),
			gain25Dot5Db(255),
			gain26Db(260),
			gain26Dot5Db(265),
			gain27Db(270),
			gain27Dot5Db(275),
			gain28Db(280),
			gain28Dot5Db(285),
			gain29Db(290),
			gain29Dot5Db(295),
			gain30Db(300),
			gain30Dot5Db(305),
			gain31Db(310),
			gain31Dot5Db(315)
			}
-- DCA possible Values The value Is multipled by 10
		TypeANtenatExist ::= INTEGER
			{
			antennaExist(1),
			antennaNotExist(2)
			}

		TypeGimabl ::= INTEGER
			{
			azScan(1),
			elScan(2),
			azelScan(3)
			}
-- 1 - Az Scan
-- 2 - El Scan
-- 3 - Az & EL Scan(TBD)
-- 
		TypeEndian ::= INTEGER
			{
			bigEndian(1),
			littleEndian(2)
			}

		TypeAzimuthScanDirection ::= INTEGER
			{
			azimuthLeft(1),
			azimuthRight(2)
			}

		TypeDelayScan ::= INTEGER (0..255)

		TypeElavationScanDirection ::= INTEGER
			{
			elvationUp(1),
			elvationDown(2)
			}

		TypeScanTimeLimit ::= INTEGER (10..999)

		TypeAzimuthValue ::= INTEGER (0..450)

		TypeElavationValue ::= INTEGER (0..20)

		TypeAntnnaPowerSupplyState ::= INTEGER
			{
			antnnaPowerSupplyOn(1),
			antnnaPowerSupplyOff(2)
			}

		TypeAgcDesiredLevel ::= INTEGER (0..127)

		TypeAcmModeOperation ::= INTEGER
			{
			acmModeOFF(1),
			acmModeLinkBitRateLimit(2),
			acmModeBandWidthLimit(3)
			}
		TypeFrequencyHopNumber ::= INTEGER
			{
			frequencyHopMulti(0),
			frequencyHopSingle(15)
			}


		TypeLinkBitRateLimit ::= INTEGER
			{
			linkbatRate2M(1),
			linkbatRate4M(2),
			linkbatRate8M(3),
			linkbatRate16M(4),
			linkbatRate34M(5),
			linkbatRate52M(6),
			linkbatRate100M(7)
			}

		TypeBandWidthLimit ::= INTEGER
			{
			limit1dot25M(1),
			limitUpto2dot5M(2),
			limitUpto5M(3),
			limitUpto10M(4),
			limitUpto20M(5),
			limitUpto32M(6)
			}

		TypeACMTaskState ::= INTEGER
			{
			acmIdle(1),
			acmWaitRspToAcmMode(2),
			acmWaitRspToOerationMode(3),
			acmTestLink(4)
			}

		TypeAcmDirection ::= INTEGER
			{
			idleDirection(1),
			upDirection(2),
			downDirection(3)
			}

		TypeApcPowerDirection ::= INTEGER
			{
			idleDirectionState(1),
			upDirectionState(2),
			downDirectionState(3)
			}
			
		TypeFrequencyConfiguration	::= INTEGER
			{
			frequency1(1),
			frequency2(2),
			frequency3(3),
			frequency4(4)
			}
			
		TypeForceUpdate	::=INTEGER
			{
			forceUpdateOFF(0),
			forceUpdateON(1)
			}
			
		TypeAntennaRotatorStatus ::=INTEGER
			{
			antennaRotatorIDLE(1),
			antennaRotatorEXE(2),
 			antennaRotatorABORT(3),
 			antennaRotatorQUEUED(4),
 			antennaRotatorERROR(5),
 			antennaRotatorBOOT(6)
 			}
 					TypeSpiClockCntrol	::= INTEGER
			{
			 rate13Mhz(1),
			 rate3point5Mhz(2)
			}
		TypePllPowerEnable	::= INTEGER
			{
			 pllPowerOFF(1),
			 pllPowerON(2)
			}
		
		TypeLnaByPassEnable	::= INTEGER
			{
			 lnaByPassDisable(1),
			 lnaByPassEnable(2)
			}

		TypeLoopbackEnable	::= INTEGER
			{
			 loopBackEnable(1),
			 loopBackDisable(2)
			}
        
        TypeRssiOnOff  ::= INTEGER
	     {
		  rssiON(1),
		  rssiOFF(2)
		 }

        TypeSawFilterSelect ::= INTEGER
	     {
		  saw32Mhz(1),
		  saw11Mhz(2),
		  saw5Point5Mhz(3)

		 }
 
        TypeTxRmsDetector	::= INTEGER
	     {
		  lAna(1),
		  tRansiver(2)
		 }
        
		TypeEpromWriteProtect  ::= INTEGER
		{
		 protectDisable(1),
		 protectEnable(2)
		
		}
		
		TypeVVAValue ::= INTEGER (0..1023)   
		TypeAntennaSpeed ::= INTEGER
		{
		speed1(1),
		speed2(2),
		speed3(3),
		speed4(4)
		}   
		
		TypeEnableBank ::= INTEGER
		{           
		   bank0Enable(0),
		   bank1Enable(1),
           disable(2)		   
        }  
         
         TypeBank ::= INTEGER
         {
         bank0(0),
         bank1(1)
         }
         
         TypeKey ::= INTEGER
         {
		 keyHop(0),
		 keyMarker(1),
         keyA(2),
         keyB(3),
         keyC(4)
         }
         BoolType ::= INTEGER
         {
			 false(0),
			 true(1)
         }	
		 DelKeyType ::= INTEGER
         {
			 bank0Delete(0),
			 bank1Delete(1)
         }
		
		

--
-- Node definitions
--
	
--  Node definitions
-- 
-- 1.3.6.1.4.1.16215
		-- 1.3.6.1.4.1.16215
		elbit OBJECT IDENTIFIER ::= { enterprises 16215 }

		
--  1.3.6.1.4.1.16215.1
		-- 1.3.6.1.4.1.16215.1
		land OBJECT IDENTIFIER ::= { elbit 1 }

		
--  1.3.6.1.4.1.16215.1.16
		-- 1.3.6.1.4.1.16215.1.16
		grx8000 OBJECT IDENTIFIER ::= { land 16 }

		
--  1.3.6.1.4.1.16215.1.16.1
		-- 1.3.6.1.4.1.16215.1.16.2
		odu OBJECT IDENTIFIER ::= { grx8000 2 }

		
		-- 1.3.6.1.4.1.16215.1.16.2.1
		commonSettings OBJECT IDENTIFIER ::= { odu 1 } 
		
		
		
		-- 1.3.6.1.4.1.16215.1.16.2.1.1
		hopFixMode OBJECT-TYPE
			SYNTAX TypeHopFixMode
			MAX-ACCESS read-write
			STATUS current
			DESCRIPTION
				"Select Fix Or Hop Mode.
				DEFVAL { 1 }
				InDB = YES
				TypeInDB=UCHAR
				ELBIT_PERM(0x00000003)
				ADMIN_PERM(0x00000003)
				TECH_PERM(0x00000003)
				USER_PERM(0x00000003)"
			::= { commonSettings 1 }

				
		-- 1.3.6.1.4.1.16215.1.16.2.1.4
		acmOperationMode OBJECT-TYPE
			SYNTAX TypeAcmModeOperation
			MAX-ACCESS read-write
			STATUS current
			DESCRIPTION
				"ACM operation Mode to enable AC in one of 2 options or to disable it
				DEFVAL { 1}
				InDB = YES
				TypeInDB=UCHAR
				ELBIT_PERM(0x00000006)
				ADMIN_PERM(0x00000006)
				TECH_PERM(0x00000006)
				USER_PERM(0x00000006)"
			::= { commonSettings 4 }

		
		-- 1.3.6.1.4.1.16215.1.16.2.1.5
		acmRateLimitParam OBJECT-TYPE
			SYNTAX TypeLinkBitRateLimit
			MAX-ACCESS read-write
			STATUS current
			DESCRIPTION
				"if acm works at rate limit this parameter handles the rate limit parameter
				DEFVAL { 1}
				InDB = YES
				TypeInDB=UCHAR
				ELBIT_PERM(0x00000006)
				ADMIN_PERM(0x00000006)
				TECH_PERM(0x00000006)
				USER_PERM(0x00000006)"
			::= { commonSettings 5 }

		
		-- 1.3.6.1.4.1.16215.1.16.2.1.6
		acmBWLimitParam OBJECT-TYPE
			SYNTAX TypeBandWidthLimit
			MAX-ACCESS read-write
			STATUS current
			DESCRIPTION
				"if acm works at rate limit this parameter handles the rate limit parameter
				DEFVAL { 1}
				InDB = YES
				TypeInDB=UCHAR
				ELBIT_PERM(0x00000006)
				ADMIN_PERM(0x00000006)
				TECH_PERM(0x00000006)
				USER_PERM(0x00000006)"
			::= { commonSettings 6 }

		
		-- 1.3.6.1.4.1.16215.1.16.2.1.7
		acmTaskTimeOut OBJECT-TYPE
			SYNTAX Integer32 (30..100)
			MAX-ACCESS read-only
			STATUS current
			DESCRIPTION
				"ACM time out to deceide
				DEFVAL {60}
				InDB = NO
				"
			::= { commonSettings 7 }

		
		-- 1.3.6.1.4.1.16215.1.16.2.1.8
		acmTaskState OBJECT-TYPE
			SYNTAX TypeACMTaskState
			MAX-ACCESS read-only
			STATUS current
			DESCRIPTION
				"Describe the diffrent states withint ACM task
				DEFVAL { 0 }
				InDB = NO"
			::= { commonSettings 8 }

		
		-- 1.3.6.1.4.1.16215.1.16.2.1.9
		acmNextStep OBJECT-TYPE
			SYNTAX TypeAcmDirection
			MAX-ACCESS read-only
			STATUS current
			DESCRIPTION
				"Describe the next step disered by ACM
				DDEFVAL { 0 }
				InDB = NO"
			::= { commonSettings 9 }

		
		-- 1.3.6.1.4.1.16215.1.16.2.1.10
		acmRateLimitStatus OBJECT-TYPE
			SYNTAX TypeLinkBitRateLimit
			MAX-ACCESS read-only
			STATUS current
			DESCRIPTION
				"Describe the The Current Rate limit in Link
				DDEFVAL { 0 }
				InDB = NO"
			::= { commonSettings 10 }

		
		-- 1.3.6.1.4.1.16215.1.16.2.1.11
		acmBwLimitStatus OBJECT-TYPE
			SYNTAX TypeBandWidthLimit
			MAX-ACCESS read-only
			STATUS current
			DESCRIPTION
				"Describe the The Current BW limit in Link
				DDEFVAL { 0 }
				InDB = NO"
			::= { commonSettings 11 }

		
--  1.3.6.1.4.1.16215.1.16.1.1
		-- 1.3.6.1.4.1.16215.1.16.2.2
		identifications OBJECT IDENTIFIER ::= { odu 2 }

		
		-- 1.3.6.1.4.1.16215.1.16.2.2.1
		oduUnitType OBJECT-TYPE
			SYNTAX OCTET STRING (SIZE (0..255))
			MAX-ACCESS read-only
			STATUS current
			DESCRIPTION
				"ODU unit type.
				InDB = NO"
			::= { identifications 1 }

		
		-- 1.3.6.1.4.1.16215.1.16.2.2.2
		oduUnitVersion OBJECT-TYPE
			SYNTAX OCTET STRING (SIZE (0..255))
			MAX-ACCESS read-only
			STATUS current
			DESCRIPTION
				"Unit software/hardware version.
				InDB = NO"
			::= { identifications 2 }

		
		-- 1.3.6.1.4.1.16215.1.16.2.2.3
		oduCustomer OBJECT-TYPE
			SYNTAX OCTET STRING (SIZE (0..255))
			MAX-ACCESS read-only
			STATUS current
			DESCRIPTION
				"custumer.
				InDB = NO"
			::= { identifications 3 }

		
--  1.3.6.1.4.1.16215.1.16.1.2
		-- 1.3.6.1.4.1.16215.1.16.2.3
		configuration OBJECT IDENTIFIER ::= { odu 3 }

		
		-- 1.3.6.1.4.1.16215.1.16.2.3.1
		oduInterleaver OBJECT-TYPE
			SYNTAX TypeShortLong
			MAX-ACCESS read-write
			STATUS current
			DESCRIPTION
				"Link modem Interleaver .
				DEFVAL { 1 }
				InDB = YES
				TypeInDB=UCHAR
				ELBIT_PERM(0x00000003)
				ADMIN_PERM(0x00000000)
				TECH_PERM(0x00000000)
				USER_PERM(0x00000000)"
			::= { configuration 1 }

		
		-- 1.3.6.1.4.1.16215.1.16.2.3.2
		oduFIFO OBJECT-TYPE
			SYNTAX TypeShortLong
			MAX-ACCESS read-write
			STATUS current
			DESCRIPTION
				"FIFO value in FPGA
				DEFVAL { 01 }
				InDB = YES
				TypeInDB=UCHAR
				ELBIT_PERM(0x00000003)
				ADMIN_PERM(0x00000000)
				TECH_PERM(0x00000000)
				USER_PERM(0x00000000)"
			::= { configuration 2 }

		
--  1.3.6.1.4.1.16215.1.16.1.3
		-- 1.3.6.1.4.1.16215.1.16.2.4
		setupFix OBJECT IDENTIFIER ::= { odu 4 }

		
		-- 1.3.6.1.4.1.16215.1.16.2.4.1
		oduTxFrequencyFF OBJECT-TYPE
			SYNTAX TypeFrequency
			UNITS "Khz"
			MAX-ACCESS read-write
			STATUS current
			DESCRIPTION
				"Transmit Frequency(in KHz),FreqMode FF.
				DEFVAL{4450000}
				InDB = YES
				TypeInDB=ULONG
				ELBIT_PERM(0xFFFFFFFF)
				ADMIN_PERM(0xFFFFFFFF)
				TECH_PERM(0xFFFFFFFF)
				USER_PERM(0xFFFFFFFF)"
			::= { setupFix 1 }

		
		-- 1.3.6.1.4.1.16215.1.16.2.4.2
		oduRxFrequencyFF OBJECT-TYPE
			SYNTAX TypeFrequency
			UNITS "Khz"
			MAX-ACCESS read-write
			STATUS current
			DESCRIPTION
				"Receive Frequency(in KHz),FreqMode FF.
				DEFVAL{4750000}
				InDB = YES
				TypeInDB=ULONG
				ELBIT_PERM(0xFFFFFFFF)
				ADMIN_PERM(0xFFFFFFFF)
				TECH_PERM(0xFFFFFFFF)
				USER_PERM(0xFFFFFFFF)"
			::= { setupFix 2 }

		
		-- 1.3.6.1.4.1.16215.1.16.2.4.3
		oduGrcMode OBJECT-TYPE
			SYNTAX TypeGrcMode
			MAX-ACCESS read-write
			STATUS current
			DESCRIPTION
				"Odu FIX working mode by default is point to point.
				DEFVAL { 0 }
				InDB = YES
				TypeInDB=UCHAR
				ELBIT_PERM(0x0000000F)
				ADMIN_PERM(0x0000000F)
				TECH_PERM(0x0000000F)
				USER_PERM(0x0000000F)"
			::= { setupFix 3 }

		
		-- 1.3.6.1.4.1.16215.1.16.2.4.4
		fixspare1 OBJECT-TYPE
			SYNTAX Integer32
			MAX-ACCESS not-accessible
			STATUS current
			DESCRIPTION
				"DEFVAL { 0 }
				InDB = NO
				TypeInDB=UCHAR
				ELBIT_PERM(0x0000000F)
				ADMIN_PERM(0x0000000F)
				TECH_PERM(0x0000000F)
				USER_PERM(0x0000000F)"
			::= { setupFix 4 }

		
		-- 1.3.6.1.4.1.16215.1.16.2.4.5
		fixspare2 OBJECT-TYPE
			SYNTAX Integer32
			MAX-ACCESS not-accessible
			STATUS current
			DESCRIPTION
				"DEFVAL { 0 }
				InDB = NO
				TypeInDB=UCHAR
				ELBIT_PERM(0x0000000F)
				ADMIN_PERM(0x0000000F)
				TECH_PERM(0x0000000F)
				USER_PERM(0x0000000F)"
			::= { setupFix 5 }

		
		-- 1.3.6.1.4.1.16215.1.16.2.4.6
		oduTxLinkModem OBJECT-TYPE
			SYNTAX TypeModem
			MAX-ACCESS read-write
			STATUS current
			DESCRIPTION
				"Tranmit Link modem modulation type default is 16QAM.
				DEFVAL { 1 }
				InDB = YES
				TypeInDB=UCHAR
				ELBIT_PERM(0x00000007)
				ADMIN_PERM(0x00000007)
				TECH_PERM(0x00000007)
				USER_PERM(0x00000007)"
			::= { setupFix 6 }

		
		-- 1.3.6.1.4.1.16215.1.16.2.4.7
		oduTxLinkBitRateQPSK OBJECT-TYPE
			SYNTAX TypeLinkBitRate
			UNITS "Mb/s"
			MAX-ACCESS read-write
			STATUS current
			DESCRIPTION
				"Tx Link bit rate in case of Tx Link modem 1s QPSK by default it's value is 16MB/s.
				DEFVAL { 5 }
				InDB = YES
				TypeInDB=UCHAR
				ELBIT_PERM(0x000001F)
				ADMIN_PERM(0x0000001F)
				TECH_PERM(0x0000001F)
				USER_PERM(0x0000001F)"
			::= { setupFix 7 }

		
		-- 1.3.6.1.4.1.16215.1.16.2.4.8
		oduTxLinkBitRate16QAM OBJECT-TYPE
			SYNTAX TypeLinkBitRate
			UNITS "MB/s"
			MAX-ACCESS read-write
			STATUS current
			DESCRIPTION
				"Tx Link bit rate in case of Tx Link modem 1s 16QAM by default it's value is 16MB/s.
				DEFVAL { 5 }
				InDB = YES
				TypeInDB=UCHAR
				ELBIT_PERM(0x00000FF)
				ADMIN_PERM(0x000000FF)
				TECH_PERM(0x000000FF)
				USER_PERM(0x000000FF)"
			::= { setupFix 8 }

		
		-- 1.3.6.1.4.1.16215.1.16.2.4.9
		oduTxLinkBitRate64QAM OBJECT-TYPE
			SYNTAX TypeLinkBitRate
			UNITS "MB/s"
			MAX-ACCESS read-write
			STATUS current
			DESCRIPTION
				"Tx Link bit rate in case of Tx Link modem 1s 64QAM by default it's value is 16MB/s.
				DEFVAL { 5 }
				InDB = YES
				TypeInDB=UCHAR
				ELBIT_PERM(0x00000F8)
				ADMIN_PERM(0x000000F8)
				TECH_PERM(0x000000F8)
				USER_PERM(0x000000F8)"
			::= { setupFix 9 }

		
		-- 1.3.6.1.4.1.16215.1.16.2.4.10
		oduRxLinkModem OBJECT-TYPE
			SYNTAX TypeModem
			MAX-ACCESS read-write
			STATUS current
			DESCRIPTION
				"ODU Rx Link modem Type by default is 16QAM
				DEFVAL { 1 }
				InDB = YES
				TypeInDB=UCHAR
				ELBIT_PERM(0x00000007)
				ADMIN_PERM(0x00000007)
				TECH_PERM(0x00000007)
				USER_PERM(0x00000007)"
			::= { setupFix 10 }

		
		-- 1.3.6.1.4.1.16215.1.16.2.4.11
		oduRxLinkBitRateQPSK OBJECT-TYPE
			SYNTAX TypeLinkBitRate
			UNITS "MB/s"
			MAX-ACCESS read-write
			STATUS current
			DESCRIPTION
				"Rx Link bit rate in case of Rx Link modem 1s QPSK by default it's value is 16MB/s.
				DEFVAL { 5 }
				InDB = YES
				TypeInDB=UCHAR
				ELBIT_PERM(0x000001F)
				ADMIN_PERM(0x0000001F)
				TECH_PERM(0x0000001F)
				USER_PERM(0x0000001F)"
			::= { setupFix 11 }

		
		-- 1.3.6.1.4.1.16215.1.16.2.4.12
		oduRxLinkBitRate16QAM OBJECT-TYPE
			SYNTAX TypeLinkBitRate
			UNITS "MB/s"
			MAX-ACCESS read-write
			STATUS current
			DESCRIPTION
				"Rx Link bit rate in case of Rx Link modem 1s 16QAM by default it's value is 16MB/s.
				DEFVAL { 5 }
				InDB = YES
				TypeInDB=UCHAR
				ELBIT_PERM(0x00000FF)
				ADMIN_PERM(0x000000FF)
				TECH_PERM(0x000000FF)
				USER_PERM(0x000000FF)"
			::= { setupFix 12 }

		
		-- 1.3.6.1.4.1.16215.1.16.2.4.13
		oduRxLinkBitRate64QAM OBJECT-TYPE
			SYNTAX TypeLinkBitRate
			UNITS "MB/s"
			MAX-ACCESS read-write
			STATUS current
			DESCRIPTION
				"Rx Link bit rate in case of Rx Link modem 1s 64QAM by default it's value is 16MB/s.
				DEFVAL { 5 }
				InDB = YES
				TypeInDB=UCHAR
				ELBIT_PERM(0x00000F8)
				ADMIN_PERM(0x000000F8)
				TECH_PERM(0x000000F8)
				USER_PERM(0x000000F8)"
			::= { setupFix 13 }

		
		-- 1.3.6.1.4.1.16215.1.16.2.4.14
		oduEmergency OBJECT-TYPE
			SYNTAX TypeOnOff
			MAX-ACCESS read-write
			STATUS current
			DESCRIPTION
				"Emergency state is - state to establish RF LINK SITE in QPSK 2Mb/s rate 
				Normaly this parameter is OFF
				DEFVAL { 0 }
				InDB = YES
				TypeInDB=UCHAR
				ELBIT_PERM(0x00000003)
				ADMIN_PERM(0x00000003)
				TECH_PERM(0x00000003)
				USER_PERM(0x00000003)"
			::= { setupFix 14 }

		
		-- 1.3.6.1.4.1.16215.1.16.2.4.15
		oduAFC OBJECT-TYPE
			SYNTAX TypeOnOff
			MAX-ACCESS read-write
			STATUS current
			DESCRIPTION
				"Afc mode relevant for PTP mode it should be activate after RF link works OK.
				DEFVAL { 0 }
				InDB = YES
				TypeInDB=UCHAR
				ELBIT_PERM(0x00000003)
				ADMIN_PERM(0x00000003)
				TECH_PERM(0x00000003)
				USER_PERM(0x00000003)"
			::= { setupFix 15 }

		
		-- 1.3.6.1.4.1.16215.1.16.2.4.16
		oduTxCWenable OBJECT-TYPE
			SYNTAX TypeOnOff
			MAX-ACCESS read-write
			STATUS current
			DESCRIPTION
				"Tx cw means that modem is Tranmit CW signal - normaly the modem transmit normal signal - for Testing the value can Be On.
				DEFVAL { 1 }
				InDB = YES
				TypeInDB=UCHAR
				ELBIT_PERM(0x00000003)
				ADMIN_PERM(0x00000003)
				TECH_PERM(0x00000003)
				USER_PERM(0x00000003)"
			::= { setupFix 16 }

		
		-- 1.3.6.1.4.1.16215.1.16.2.4.17
		oduParLoadMode OBJECT-TYPE
			SYNTAX TypeUpLoadMode
			MAX-ACCESS read-write
			STATUS current
			DESCRIPTION
				"This paramer enable to set up full page of parameters at once.
				DEFVAL { 0 }
				InDB = NO
				ELBIT_PERM(0x0000001C)
				ADMIN_PERM(0x0000001C)
				TECH_PERM(0x0000001C)
				USER_PERM(0x0000001C)"
			::= { setupFix 17 }

		
		-- 1.3.6.1.4.1.16215.1.16.2.4.18
		broadcomtxiF1 OBJECT-TYPE
			SYNTAX Integer32
			MAX-ACCESS read-write
			STATUS current
			DESCRIPTION
				"BroadCom Tx  1 IF Frequency
				InDB = NO"
			::= { setupFix 18 }

		
		-- 1.3.6.1.4.1.16215.1.16.2.4.19
		broadcomtxiF2 OBJECT-TYPE
			SYNTAX Integer32
			MAX-ACCESS read-write
			STATUS current
			DESCRIPTION
				"BroadCom Tx  2 IF Frequency
				InDB = NO"
			::= { setupFix 19 }

		
		-- 1.3.6.1.4.1.16215.1.16.2.4.20
		broadcomrxiF1 OBJECT-TYPE
			SYNTAX Integer32
			MAX-ACCESS read-write
			STATUS current
			DESCRIPTION
				"BroadCom Rx 1 IF Frequency
				InDB = NO"
			::= { setupFix 20 }

		
		-- 1.3.6.1.4.1.16215.1.16.2.4.21
		broadcomrxiF2 OBJECT-TYPE
			SYNTAX Integer32
			MAX-ACCESS read-write
			STATUS current
			DESCRIPTION
				"BroadCom Rx 2 IF Frequency
				InDB = NO"
			::= { setupFix 21 }

		
		-- 1.3.6.1.4.1.16215.1.16.2.5
		setupHop OBJECT IDENTIFIER ::= { odu 5 }

		-- 1.3.6.1.4.1.16215.1.16.2.5.1
		hopWorkingMode OBJECT-TYPE
			SYNTAX TypeGrcMode
			MAX-ACCESS read-write
			STATUS current
			DESCRIPTION
				"Odu HOP working mode by default is point to point.
				DEFVAL { 0 }
				InDB = YES
				TypeInDB=UCHAR
				ELBIT_PERM(0x0000001E)
				ADMIN_PERM(0x0000001E)
				TECH_PERM(0x0000001E)
				USER_PERM(0x0000001E)"
			::= { setupHop 1 }

		
		-- 1.3.6.1.4.1.16215.1.16.2.5.2
		hopTxRate OBJECT-TYPE
			SYNTAX TypehopRate
			MAX-ACCESS read-write
			STATUS current
			DESCRIPTION
				"Hop Tx Rate
				DEFVAL { 0 }
				InDB = YES
				TypeInDB=UCHAR
				ELBIT_PERM(0x00000003)
				ADMIN_PERM(0x00000003)
				TECH_PERM(0x00000003)
				USER_PERM(0x00000003)"
			::= { setupHop 2 }

		
		-- 1.3.6.1.4.1.16215.1.16.2.5.3
		hopRxRate OBJECT-TYPE
			SYNTAX TypehopRate
			MAX-ACCESS read-write
			STATUS current
			DESCRIPTION
				"Hop Rx Rate
				DEFVAL { 0 }
				InDB = YES
				TypeInDB=UCHAR
				ELBIT_PERM(0x00000003)
				ADMIN_PERM(0x00000003)
				TECH_PERM(0x00000003)
				USER_PERM(0x00000003)"
			::= { setupHop 3 }

		
		-- 1.3.6.1.4.1.16215.1.16.2.5.4
		spare1 OBJECT-TYPE
			SYNTAX Integer32
			MAX-ACCESS read-write
			STATUS current
			DESCRIPTION
				"Spare
				DEFVAL { 1}
				InDB = YES
				TypeInDB=UCHAR
				ELBIT_PERM(0x00000006)
				ADMIN_PERM(0x00000006)
				TECH_PERM(0x00000006)
				USER_PERM(0x00000006)"
			::= { setupHop 4 }

		
		-- 1.3.6.1.4.1.16215.1.16.2.5.5
		spare2 OBJECT-TYPE
			SYNTAX Integer32
			MAX-ACCESS read-write
			STATUS current
			DESCRIPTION
				"Spare
				DEFVAL { 1}
				InDB = YES
				TypeInDB=UCHAR
				ELBIT_PERM(0x00000006)
				ADMIN_PERM(0x00000006)
				TECH_PERM(0x00000006)
				USER_PERM(0x00000006)"
			::= { setupHop 5 }

		
		-- 1.3.6.1.4.1.16215.1.16.2.5.6
		spare3 OBJECT-TYPE
			SYNTAX Integer32
			MAX-ACCESS read-write
			STATUS current
			DESCRIPTION
				"Spare
				DEFVAL { 1}
				InDB = YES
				TypeInDB=UCHAR
				ELBIT_PERM(0x00000006)
				ADMIN_PERM(0x00000006)
				TECH_PERM(0x00000006)
				USER_PERM(0x00000006)"
			::= { setupHop 6 }

		
		-- 1.3.6.1.4.1.16215.1.16.2.5.7
		spare4 OBJECT-TYPE
			SYNTAX Integer32
			MAX-ACCESS read-write
			STATUS current
			DESCRIPTION
				"Spare
				DEFVAL { 1}
				InDB = YES
				TypeInDB=UCHAR
				ELBIT_PERM(0x00000006)
				ADMIN_PERM(0x00000006)
				TECH_PERM(0x00000006)
				USER_PERM(0x00000006)"
			::= { setupHop 7 }

		
		-- 1.3.6.1.4.1.16215.1.16.2.5.8
		hoptxBandSelect OBJECT-TYPE
			SYNTAX TypeBandSelect
			MAX-ACCESS read-write
			STATUS current
			DESCRIPTION
				"Band Select on Tx Side
				DEFVAL { 1}
				InDB = YES
				TypeInDB=UCHAR
				ELBIT_PERM(0x00000006)
				ADMIN_PERM(0x00000006)
				TECH_PERM(0x00000006)
				USER_PERM(0x00000006)"
			::= { setupHop 8 }

		
		-- 1.3.6.1.4.1.16215.1.16.2.5.9
		hoptxSubBandSelect OBJECT-TYPE
			SYNTAX TypeNumberofSubBands
			MAX-ACCESS read-write
			STATUS current
			DESCRIPTION
				"Sub Band Select on Tx Side
				DEFVAL { 1}
				InDB = YES
				TypeInDB=UCHAR
				ELBIT_PERM(0x00000006)
				ADMIN_PERM(0x00000006)
				TECH_PERM(0x00000006)
				USER_PERM(0x00000006)"
			::= { setupHop 9 }

		
		-- 1.3.6.1.4.1.16215.1.16.2.5.10
		spare6 OBJECT-TYPE
			SYNTAX Integer32
			MAX-ACCESS read-write
			STATUS current
			DESCRIPTION
				"spare
				DEFVAL { 1}
				InDB = NO
				TypeInDB=UCHAR
				ELBIT_PERM(0x00000006)
				ADMIN_PERM(0x00000006)
				TECH_PERM(0x00000006)
				USER_PERM(0x00000006)"
			::= { setupHop 10 }

		
		-- 1.3.6.1.4.1.16215.1.16.2.5.11
		spare7 OBJECT-TYPE
			SYNTAX Integer32
			MAX-ACCESS read-write
			STATUS current
			DESCRIPTION
				"spare
				DEFVAL { 1}
				InDB = NO
				TypeInDB=UCHAR
				ELBIT_PERM(0x00000006)
				ADMIN_PERM(0x00000006)
				TECH_PERM(0x00000006)
				USER_PERM(0x00000006)"
			::= { setupHop 11 }

		
		-- 1.3.6.1.4.1.16215.1.16.2.5.12
		hopTxLinkMember OBJECT-TYPE
			SYNTAX TypeFrequencyMember
			MAX-ACCESS read-write
			STATUS current
			DESCRIPTION
				"Assignd Tx Link Member
				DEFVAL { 1}
				InDB = YES
				TypeInDB=UCHAR
				ELBIT_PERM(0x000000FF)
				ADMIN_PERM(0x000000FF)
				TECH_PERM(0x000000FF)
				USER_PERM(0x000000FF)"
			::= { setupHop 12 }

		
		-- 1.3.6.1.4.1.16215.1.16.2.5.13
		hopTxLinkId OBJECT-TYPE
			SYNTAX TypeLinkId
			MAX-ACCESS read-write
			STATUS current
			DESCRIPTION
				"Assignd Tx Link ID
				DEFVAL { 1}
				InDB = YES
				TypeInDB=WORD
				ELBIT_PERM(0x000000FF)
				ADMIN_PERM(0x000000FF)
				TECH_PERM(0x000000FF)
				USER_PERM(0x000000FF)"
			::= { setupHop 13 }

		
		-- 1.3.6.1.4.1.16215.1.16.2.5.14
		hoprxBandSelect OBJECT-TYPE
			SYNTAX TypeBandSelect
			MAX-ACCESS read-write
			STATUS current
			DESCRIPTION
				"Band Select on Rx Side
				DEFVAL { 1}
				InDB = YES
				TypeInDB=UCHAR
				ELBIT_PERM(0x00000006)
				ADMIN_PERM(0x00000006)
				TECH_PERM(0x00000006)
				USER_PERM(0x00000006)"
			::= { setupHop 14 }

		
		-- 1.3.6.1.4.1.16215.1.16.2.5.15
		hopRxSubBandSelect OBJECT-TYPE
			SYNTAX TypeNumberofSubBands
			MAX-ACCESS read-write
			STATUS current
			DESCRIPTION
				"Sub Band Select on Rx Side
				DEFVAL { 1}
				InDB = YES
				TypeInDB=UCHAR
				ELBIT_PERM(0x00000006)
				ADMIN_PERM(0x00000006)
				TECH_PERM(0x00000006)
				USER_PERM(0x00000006)"
			::= { setupHop 15 }

		
		-- 1.3.6.1.4.1.16215.1.16.2.5.16
		spare8 OBJECT-TYPE
			SYNTAX Integer32
			MAX-ACCESS read-write
			STATUS current
			DESCRIPTION
				"pare
				DEFVAL { 1}
				InDB = YES
				TypeInDB=UCHAR
				ELBIT_PERM(0x00000006)
				ADMIN_PERM(0x00000006)
				TECH_PERM(0x00000006)
				USER_PERM(0x00000006)"
			::= { setupHop 16 }

		
		-- 1.3.6.1.4.1.16215.1.16.2.5.17
		spare9 OBJECT-TYPE
			SYNTAX Integer32
			MAX-ACCESS read-write
			STATUS current
			DESCRIPTION
				"spare
				DEFVAL { 1}
				InDB = YES
				TypeInDB=UCHAR
				ELBIT_PERM(0x00000006)
				ADMIN_PERM(0x00000006)
				TECH_PERM(0x00000006)
				USER_PERM(0x00000006)"
			::= { setupHop 17 }

		
		-- 1.3.6.1.4.1.16215.1.16.2.5.18
		hopRxLinkMember OBJECT-TYPE
			SYNTAX TypeFrequencyMember
			MAX-ACCESS read-write
			STATUS current
			DESCRIPTION
				"Assignd Rx Link Member
				DEFVAL { 1}
				InDB = YES
				TypeInDB=UCHAR
				ELBIT_PERM(0x000000FF)
				ADMIN_PERM(0x000000FF)
				TECH_PERM(0x000000FF)
				USER_PERM(0x000000FF)"
			::= { setupHop 18 }

		
		-- 1.3.6.1.4.1.16215.1.16.2.5.19
		hopRxLinkId OBJECT-TYPE
			SYNTAX TypeLinkId
			MAX-ACCESS read-write
			STATUS current
			DESCRIPTION
				"assignd Rx Link ID
				DEFVAL { 1}
				InDB = YES
				TypeInDB=WORD
				ELBIT_PERM(0x000000FF)
				ADMIN_PERM(0x000000FF)
				TECH_PERM(0x000000FF)
				USER_PERM(0x000000FF)"
			::= { setupHop 19 }

		
-- 	
		-- 1.3.6.1.4.1.16215.1.16.2.5.20
		hopFrequencyTableSelect OBJECT-TYPE
			SYNTAX TypeHopFreqTableSelect
			MAX-ACCESS read-write
			STATUS current
			DESCRIPTION
				" Select Hop Frequency Table to Use
				  DEFVAL { 0}
				  InDB = YES
				  TypeInDB=UCHAR
				  ELBIT_PERM(0x000000FF)
				  ADMIN_PERM(0x000000FF)
				  TECH_PERM(0x000000FF)
				  USER_PERM(0x000000FF)
				"
			::= { setupHop 20 }

		
		-- 1.3.6.1.4.1.16215.1.16.2.5.21
		numberOfBands OBJECT-TYPE
			SYNTAX TypeNumberOfBands
			MAX-ACCESS read-only
			STATUS current
			DESCRIPTION
				"Number Of Bands in selected table
				This parameter is read by NMS to know how many bands
				can be assign to hop
				InDB = NO"
			::= { setupHop 21 }

		
		-- 1.3.6.1.4.1.16215.1.16.2.5.22
		numberOfSubBands OBJECT-TYPE
			SYNTAX TypeNumberofSubBands
			MAX-ACCESS read-only
			STATUS current
			DESCRIPTION
				"Number Of Sub Bands in selected table
				This parameter is read by NMS to know how many bands
				can be assign to hop
				InDB = NO
				"
			::= { setupHop 22 }

		
		-- 1.3.6.1.4.1.16215.1.16.2.5.23
		numberOfFrequeniesInSubBand OBJECT-TYPE
			SYNTAX TypeNumberOfFrequenciesInBand
			MAX-ACCESS read-only
			STATUS current
			DESCRIPTION
				"Number Of frequencies in band
				This parameter is read by NMS to know how many bands
				can be assign to hop
				InDB = NO"
			::= { setupHop 23 }

		
		-- 1.3.6.1.4.1.16215.1.16.2.5.24
		hopFrequencyKeySelect OBJECT-TYPE
			SYNTAX TypeHopFrequencyKeySelect
			MAX-ACCESS read-write
			STATUS current
			DESCRIPTION
				"Hop Frequency Key Select
				DEFVAL { 1}
				InDB = YES
				TypeInDB=UCHAR
				ELBIT_PERM(0x000000FF)
				ADMIN_PERM(0x000000FF)
				TECH_PERM(0x000000FF)
				USER_PERM(0x000000FF)"
			::= { setupHop 24 }

		
		-- 1.3.6.1.4.1.16215.1.16.2.5.25
		hopParLoad OBJECT-TYPE
			SYNTAX TypeUpLoadMode
			MAX-ACCESS read-write
			STATUS current
			DESCRIPTION
				"Hop set up parameters mode can be only in Set page and load parameters to HW
				InDB = NO
				"
			::= { setupHop 25 }

		-- 1.3.6.1.4.1.16215.1.16.2.5.26
		carrierWorkingBitmap OBJECT-TYPE
			SYNTAX TypeCarrierBitmapMode
			MAX-ACCESS read-write
			STATUS current
			DESCRIPTION
				"Carrier bitmap 1 - carrier enable, carrier1 is LSB bit
				DEFVAL { 0 }
				InDB = YES
				TypeInDB=UCHAR
				ELBIT_PERM(0x000000FF)
				ADMIN_PERM(0x000000FF)
				TECH_PERM(0x000000FF)
				USER_PERM(0x000000FF)"
			::= { setupHop 26 }

			
--  1.3.6.1.4.1.16215.1.16.1.4
		-- 1.3.6.1.4.1.16215.1.16.2.6
		ipAddress OBJECT IDENTIFIER ::= { odu 6 }

		
		-- 1.3.6.1.4.1.16215.1.16.2.6.1
		oduDefaultGateWay OBJECT-TYPE
			SYNTAX OCTET STRING (SIZE (0..255))
			MAX-ACCESS read-write
			STATUS current
			DESCRIPTION
				"Default GateWay For communicate GRC via router 
				DEFVAL { 0x010101C8 }
				InDB = YES
				TypeInDB=ULONG
				ELBIT_PERM(0xFFFFFFFF)
				ADMIN_PERM(0xFFFFFFFF)
				TECH_PERM(0xFFFFFFFF)
				USER_PERM(0xFFFFFFFF)"
			::= { ipAddress 1 }

		
		-- 1.3.6.1.4.1.16215.1.16.2.6.2
		oduManagementIP OBJECT-TYPE
			SYNTAX OCTET STRING (SIZE (0..255))
			MAX-ACCESS read-write
			STATUS current
			DESCRIPTION
				"Ip address for Managent only.
				DEFVAL { 0x01010164 }
				InDB = YES
				TypeInDB=ULONG
				ELBIT_PERM(0xFFFFFFFF)
				ADMIN_PERM(0xFFFFFFFF)
				TECH_PERM(0xFFFFFFFF)
				USER_PERM(0xFFFFFFFF)"
			::= { ipAddress 2 }

		
		-- 1.3.6.1.4.1.16215.1.16.2.6.3
		oduMngSubNetMask OBJECT-TYPE
			SYNTAX OCTET STRING (SIZE (0..255))
			MAX-ACCESS read-write
			STATUS current
			DESCRIPTION
				"Subnet mask of management Ip.
				It is recomend that managment IP should be diffrent IP address from Link IP and in a differnet subnet
				DEFVAL { 0xFFFFFF00 }
				InDB = YES
				TypeInDB=ULONG
				ELBIT_PERM(0xFFFFFFFF)
				ADMIN_PERM(0xFFFFFFFF)
				TECH_PERM(0xFFFFFFFF)
				USER_PERM(0xFFFFFFFF)
				"
			::= { ipAddress 3 }

		
		-- 1.3.6.1.4.1.16215.1.16.2.6.4
		oduLinkIP OBJECT-TYPE
			SYNTAX OCTET STRING (SIZE (0..255))
			MAX-ACCESS read-write
			STATUS current
			DESCRIPTION
				"Link Ip is for communicate between GRC for Power managemnt and call system.
				Do not use for managment.
				In case of working PTP the GRC's should work in pairs when the last digit of IP should be 2 and the remote is 3 or 4 and the remote is 5  and so on.
				Some numbers are ileagal 10,11,20,21
				In case the GRC is MPT2P the last digit should be 1.
				In case the GRC is SP1 the last digit should be 11.
				In case the GRC is SP2 the last digit should be 21.
				DEFVAL { 0x01010102 }
				InDB = YES
				TypeInDB=ULONG
				ELBIT_PERM(0xFFFFFFFF)
				ADMIN_PERM(0xFFFFFFFF)
				TECH_PERM(0xFFFFFFFF)
				USER_PERM(0xFFFFFFFF)"
			::= { ipAddress 4 }

		
		-- 1.3.6.1.4.1.16215.1.16.2.6.5
		hostTrapsIP OBJECT-TYPE
			SYNTAX OCTET STRING (SIZE (0..255))
			MAX-ACCESS read-write
			STATUS current
			DESCRIPTION
				"Host IP means address to send csv files 
				DEFVAL { 0x010101105 }
				InDB = YES
				TypeInDB=ULONG
				ELBIT_PERM(0xFFFFFFFF)
				ADMIN_PERM(0xFFFFFFFF)
				TECH_PERM(0xFFFFFFFF)
				USER_PERM(0xFFFFFFFF)"
			::= { ipAddress 5 }

		
		-- 1.3.6.1.4.1.16215.1.16.2.7
		dac OBJECT IDENTIFIER ::= { odu 7 }

		
		-- 1.3.6.1.4.1.16215.1.16.2.7.1
		oduDAC1LvlQPSKUpTo34M OBJECT-TYPE
			SYNTAX INTEGER (0..63)
			MAX-ACCESS read-write
			STATUS current
			DESCRIPTION
				"Calbe Modem DAC level for QPSK 34M.
				DEFVAL { 63 }
				InDB = YES
				TypeInDB=UCHAR
				ELBIT_PERM(0xFFFFFFFF)
				ADMIN_PERM(0x00000000)
				TECH_PERM(0x00000000)
				USER_PERM(0x00000000)"
			::= { dac 1 }

		
		-- 1.3.6.1.4.1.16215.1.16.2.7.2
		oduDAC1Lvl16QAMupTo52M OBJECT-TYPE
			SYNTAX INTEGER (0..63)
			MAX-ACCESS read-write
			STATUS current
			DESCRIPTION
				"Calbe Modem DAC level for 16QAM up to 52M.
				DEFVAL { 63}
				InDB = YES
				TypeInDB=UCHAR
				ELBIT_PERM(0xFFFFFFFF)
				ADMIN_PERM(0x00000000)
				TECH_PERM(0x00000000)
				USER_PERM(0x00000000)"
			::= { dac 2 }

		
		-- 1.3.6.1.4.1.16215.1.16.2.7.3
		oduDAC1Lvl16QAMupTo104M OBJECT-TYPE
			SYNTAX INTEGER (0..63)
			MAX-ACCESS read-write
			STATUS current
			DESCRIPTION
				"Calbe Modem DAC level for 16QAM up to 104M.
				DEFVAL { 63 }
				InDB = YES
				TypeInDB=UCHAR
				ELBIT_PERM(0xFFFFFFFF)
				ADMIN_PERM(0x00000000)
				TECH_PERM(0x00000000)
				USER_PERM(0x00000000)"
			::= { dac 3 }

		
		-- 1.3.6.1.4.1.16215.1.16.2.7.4
		oduDAC1Lvl64QAMupTo52M OBJECT-TYPE
			SYNTAX INTEGER (0..63)
			MAX-ACCESS read-write
			STATUS current
			DESCRIPTION
				"Calbe Modem DAC level for 64QAM up to 52M.
				DEFVAL {63 }
				InDB = YES
				TypeInDB=UCHAR
				ELBIT_PERM(0xFFFFFFFF)
				ADMIN_PERM(0x00000000)
				TECH_PERM(0x00000000)
				USER_PERM(0x00000000)"
			::= { dac 4 }

		
		-- 1.3.6.1.4.1.16215.1.16.2.7.5
		oduDAC1Lvl64QAMupTo104M OBJECT-TYPE
			SYNTAX INTEGER (0..63)
			MAX-ACCESS read-write
			STATUS current
			DESCRIPTION
				"Calbe Modem DAC level for 64QAM up to 104M.
				DEFVAL { 63 }
				InDB = YES
				TypeInDB=UCHAR
				ELBIT_PERM(0xFFFFFFFF)
				ADMIN_PERM(0x00000000)
				TECH_PERM(0x00000000)
				USER_PERM(0x00000000)"
			::= { dac 5 }

		
		-- 1.3.6.1.4.1.16215.1.16.2.7.6
		oduDAC2LvlQPSKUpTo34M OBJECT-TYPE
			SYNTAX INTEGER (0..63)
			MAX-ACCESS read-write
			STATUS current
			DESCRIPTION
				"Link Modem DAC level for QPSK 34M.
				DEFVAL { 63 }
				InDB = YES
				TypeInDB=UCHAR
				ELBIT_PERM(0xFFFFFFFF)
				ADMIN_PERM(0x00000000)
				TECH_PERM(0x00000000)
				USER_PERM(0x00000000)"
			::= { dac 6 }

		
		-- 1.3.6.1.4.1.16215.1.16.2.7.7
		oduDAC2Lvl16QAMupTo52M OBJECT-TYPE
			SYNTAX INTEGER (0..63)
			MAX-ACCESS read-write
			STATUS current
			DESCRIPTION
				"Link Modem DAC level for 16QAM up to 52M.
				DEFVAL { 63 }
				InDB = YES
				TypeInDB=UCHAR
				ELBIT_PERM(0xFFFFFFFF)
				ADMIN_PERM(0x00000000)
				TECH_PERM(0x00000000)
				USER_PERM(0x00000000)"
			::= { dac 7 }

		
		-- 1.3.6.1.4.1.16215.1.16.2.7.8
		oduDAC2Lvl16QAMupTo104M OBJECT-TYPE
			SYNTAX INTEGER (0..63)
			MAX-ACCESS read-write
			STATUS current
			DESCRIPTION
				"Link Modem DAC level for 64QAM up to 104M.
				DEFVAL { 63 }
				InDB = YES
				TypeInDB=UCHAR
				ELBIT_PERM(0xFFFFFFFF)
				ADMIN_PERM(0x00000000)
				TECH_PERM(0x00000000)
				USER_PERM(0x00000000)"
			::= { dac 8 }

		
		-- 1.3.6.1.4.1.16215.1.16.2.7.9
		oduDAC2Lvl64QAMupTo52M OBJECT-TYPE
			SYNTAX INTEGER (0..63)
			MAX-ACCESS read-write
			STATUS current
			DESCRIPTION
				"Link Modem DAC level for 64QAM up to 52M.
				DEFVAL { 63 }
				InDB = YES
				TypeInDB=UCHAR
				ELBIT_PERM(0xFFFFFFFF)
				ADMIN_PERM(0x00000000)
				TECH_PERM(0x00000000)
				USER_PERM(0x00000000)"
			::= { dac 9 }

		
		-- 1.3.6.1.4.1.16215.1.16.2.7.10
		oduDAC2Lvl64QAMupTo104M OBJECT-TYPE
			SYNTAX INTEGER (0..63)
			MAX-ACCESS read-write
			STATUS current
			DESCRIPTION
				"Link Modem DAC level for 64QAM up to 104M.
				DEFVAL { 63 }
				InDB = YES
				TypeInDB=UCHAR
				ELBIT_PERM(0xFFFFFFFF)
				ADMIN_PERM(0x00000000)
				TECH_PERM(0x00000000)
				USER_PERM(0x00000000)"
			::= { dac 10 }

		
--  1.3.6.1.4.1.16215.1.16.1.6
		-- 1.3.6.1.4.1.16215.1.16.2.8
		linkModemOffset OBJECT IDENTIFIER ::= { odu 8 }

		
		-- 1.3.6.1.4.1.16215.1.16.2.8.1
		odu64QAM8Moffset OBJECT-TYPE
			SYNTAX TypeIfModemOffset
			MAX-ACCESS read-write
			STATUS current
			DESCRIPTION
				"if Modem Offset from main signal in case of 8M 64QAM in link.
				The Number present 125Khz Multiply
				DEFVAL { 72 }
				InDB = YES
				TypeInDB=CHAR
				ELBIT_PERM(0xFFFFFFFF)
				ADMIN_PERM(0x00000000)
				TECH_PERM(0x00000000)
				USER_PERM(0x00000000)"
			::= { linkModemOffset 1 }

		
		-- 1.3.6.1.4.1.16215.1.16.2.8.2
		odu64QAM16Moffset OBJECT-TYPE
			SYNTAX TypeIfModemOffset
			UNITS "Mhz"
			MAX-ACCESS read-write
			STATUS current
			DESCRIPTION
				"If Modem Offset from main signal in case of 16M 64QAM in link.
				The Number present 125Khz Multiply
				DEFVAL { 72 }
				InDB = YES
				TypeInDB=CHAR
				ELBIT_PERM(0xFFFFFFFF)
				ADMIN_PERM(0x00000000)
				TECH_PERM(0x00000000)
				USER_PERM(0x00000000)"
			::= { linkModemOffset 2 }

		
		-- 1.3.6.1.4.1.16215.1.16.2.8.3
		odu64QAM34Moffset OBJECT-TYPE
			SYNTAX TypeIfModemOffset
			UNITS "Mhz"
			MAX-ACCESS read-write
			STATUS current
			DESCRIPTION
				"If Modem Offset from main signal in case of 34M 64QAM in link.
				The Number present 125Khz Multiply
				DEFVAL { 72 }
				InDB = YES
				TypeInDB=CHAR
				ELBIT_PERM(0xFFFFFFFF)
				ADMIN_PERM(0x00000000)
				TECH_PERM(0x00000000)
				USER_PERM(0x00000000)"
			::= { linkModemOffset 3 }

		
		-- 1.3.6.1.4.1.16215.1.16.2.8.4
		odu64QAM52Moffset OBJECT-TYPE
			SYNTAX TypeIfModemOffset
			UNITS "Mhz"
			MAX-ACCESS read-write
			STATUS current
			DESCRIPTION
				"If Modem Offset from main signal in case of 52M 64QAM in link.
				The Number present 125Khz Multiply
				DEFVAL { 72 }
				InDB = YES
				TypeInDB=CHAR
				ELBIT_PERM(0xFFFFFFFF)
				ADMIN_PERM(0x00000000)
				TECH_PERM(0x00000000)
				USER_PERM(0x00000000)"
			::= { linkModemOffset 4 }

		
		-- 1.3.6.1.4.1.16215.1.16.2.8.5
		odu64QAM104Moffset OBJECT-TYPE
			SYNTAX TypeIfModemOffset
			UNITS "Mhz"
			MAX-ACCESS read-write
			STATUS current
			DESCRIPTION
				"If Modem Offset from main signal in case of 1044M 64QAM in link.
				The Number present 125Khz Multiply
				DEFVAL { 72 }
				InDB = YES
				TypeInDB=CHAR
				ELBIT_PERM(0xFFFFFFFF)
				ADMIN_PERM(0x00000000)
				TECH_PERM(0x00000000)
				USER_PERM(0x00000000)"
			::= { linkModemOffset 5 }

		
		-- 1.3.6.1.4.1.16215.1.16.2.8.6
		odu16QAM2Moffset OBJECT-TYPE
			SYNTAX TypeIfModemOffset
			UNITS "Mhz"
			MAX-ACCESS read-write
			STATUS current
			DESCRIPTION
				"If Modem Offset from main signal in case of 2M 16QAM in link
				The Number present 125Khz Multiply
				DEFVAL { 72 }
				InDB = YES
				TypeInDB=CHAR
				ELBIT_PERM(0xFFFFFFFF)
				ADMIN_PERM(0x00000000)
				TECH_PERM(0x00000000)
				USER_PERM(0x00000000)."
			::= { linkModemOffset 6 }

		
		-- 1.3.6.1.4.1.16215.1.16.2.8.7
		odu16QAM4Moffset OBJECT-TYPE
			SYNTAX TypeIfModemOffset
			UNITS "Mhz"
			MAX-ACCESS read-write
			STATUS current
			DESCRIPTION
				"If Modem Offset from main signal in case of 4M 16QAM in link.
				The Number present 125Khz Multiply
				DEFVAL { 72 }
				InDB = YES
				TypeInDB=CHAR
				ELBIT_PERM(0xFFFFFFFF)
				ADMIN_PERM(0x00000000)
				TECH_PERM(0x00000000)
				USER_PERM(0x00000000)"
			::= { linkModemOffset 7 }

		
		-- 1.3.6.1.4.1.16215.1.16.2.8.8
		odu16QAM8Moffset OBJECT-TYPE
			SYNTAX TypeIfModemOffset
			UNITS "Mhz"
			MAX-ACCESS read-write
			STATUS current
			DESCRIPTION
				"If Modem Offset from main signal in case of 8M 16QAM in link.
				The Number present 125Khz Multiply
				DEFVAL { 72 }
				InDB = YES
				TypeInDB=CHAR
				ELBIT_PERM(0xFFFFFFFF)
				ADMIN_PERM(0x00000000)
				TECH_PERM(0x00000000)
				USER_PERM(0x00000000)"
			::= { linkModemOffset 8 }

		
		-- 1.3.6.1.4.1.16215.1.16.2.8.9
		odu16QAM16Moffset OBJECT-TYPE
			SYNTAX TypeIfModemOffset
			UNITS "Mhz"
			MAX-ACCESS read-write
			STATUS current
			DESCRIPTION
				"If Modem Offset from main signal in case of 16M 16QAM in link.
				The Number present 125Khz Multiply
				DEFVAL { 72 }
				InDB = YES
				TypeInDB=CHAR
				ELBIT_PERM(0xFFFFFFFF)
				ADMIN_PERM(0x00000000)
				TECH_PERM(0x00000000)
				USER_PERM(0x00000000)"
			::= { linkModemOffset 9 }

		
		-- 1.3.6.1.4.1.16215.1.16.2.8.10
		odu16QAM34Moffset OBJECT-TYPE
			SYNTAX TypeIfModemOffset
			UNITS "Mhz"
			MAX-ACCESS read-write
			STATUS current
			DESCRIPTION
				"If Modem Offset from main signal in case of 34M 16QAM in link.
				The Number present 125Khz Multiply
				DEFVAL { 72 }
				InDB = YES
				TypeInDB=CHAR
				ELBIT_PERM(0xFFFFFFFF)
				ADMIN_PERM(0x00000000)
				TECH_PERM(0x00000000)
				USER_PERM(0x00000000)"
			::= { linkModemOffset 10 }

		
		-- 1.3.6.1.4.1.16215.1.16.2.8.11
		odu16QAM52Moffset OBJECT-TYPE
			SYNTAX TypeIfModemOffset
			UNITS "Mhz"
			MAX-ACCESS read-write
			STATUS current
			DESCRIPTION
				"If Modem Offset from main signal in case of 52M 16QAM in link.
				The Number present 125Khz Multiply
				DEFVAL { 72 }
				InDB = YES
				TypeInDB=CHAR
				ELBIT_PERM(0xFFFFFFFF)
				ADMIN_PERM(0x00000000)
				TECH_PERM(0x00000000)
				USER_PERM(0x00000000)"
			::= { linkModemOffset 11 }

		
		-- 1.3.6.1.4.1.16215.1.16.2.8.12
		odu16QAM104Moffset OBJECT-TYPE
			SYNTAX TypeIfModemOffset
			UNITS "Mhz"
			MAX-ACCESS read-write
			STATUS current
			DESCRIPTION
				"If Modem Offset from main signal in case of 104M 16QAM in link.
				The Number present 125Khz Multiply
				DEFVAL { 72 }
				InDB = YES
				TypeInDB=CHAR
				ELBIT_PERM(0xFFFFFFFF)
				ADMIN_PERM(0x00000000)
				TECH_PERM(0x00000000)
				USER_PERM(0x00000000)
				"
			::= { linkModemOffset 12 }

		
		-- 1.3.6.1.4.1.16215.1.16.2.8.13
		oduQPSK1Moffset OBJECT-TYPE
			SYNTAX TypeIfModemOffset
			UNITS "Mhz"
			MAX-ACCESS read-write
			STATUS current
			DESCRIPTION
				"If Modem Offset from main signal in case of 1M QPSK in link.
				The Number present 125Khz Multiply
				DEFVAL { 72 }
				InDB = YES
				TypeInDB=CHAR
				ELBIT_PERM(0xFFFFFFFF)
				ADMIN_PERM(0x00000000)
				TECH_PERM(0x00000000)
				USER_PERM(0x00000000)"
			::= { linkModemOffset 13 }

		
		-- 1.3.6.1.4.1.16215.1.16.2.8.14
		oduQPSK2Moffset OBJECT-TYPE
			SYNTAX TypeIfModemOffset
			UNITS "Mhz"
			MAX-ACCESS read-write
			STATUS current
			DESCRIPTION
				"If Modem Offset from main signal in case of 2M QPSK in link.
				The Number present 125Khz Multiply
				DEFVAL { 72 }
				InDB = YES
				TypeInDB=CHAR
				ELBIT_PERM(0xFFFFFFFF)
				ADMIN_PERM(0x00000000)
				TECH_PERM(0x00000000)
				USER_PERM(0x00000000)"
			::= { linkModemOffset 14 }

		
		-- 1.3.6.1.4.1.16215.1.16.2.8.15
		oduQPSK4Moffset OBJECT-TYPE
			SYNTAX TypeIfModemOffset
			MAX-ACCESS read-write
			STATUS current
			DESCRIPTION
				"If Modem Offset from main signal in case of 4M QPSK in link.
				The Number present 125Khz Multiply
				DEFVAL { 72 }
				InDB = YES
				TypeInDB=CHAR
				ELBIT_PERM(0xFFFFFFFF)
				ADMIN_PERM(0x00000000)
				TECH_PERM(0x00000000)
				USER_PERM(0x00000000)"
			::= { linkModemOffset 15 }

		
		-- 1.3.6.1.4.1.16215.1.16.2.8.16
		oduQPSK8Moffset OBJECT-TYPE
			SYNTAX TypeIfModemOffset
			UNITS "Mhz"
			MAX-ACCESS read-write
			STATUS current
			DESCRIPTION
				"If Modem Offset from main signal in case of 8M QPSK in link.
				The Number present 125Khz Multiply
				DEFVAL { 72 }
				InDB = YES
				TypeInDB=CHAR
				ELBIT_PERM(0xFFFFFFFF)
				ADMIN_PERM(0x00000000)
				TECH_PERM(0x00000000)
				USER_PERM(0x00000000)"
			::= { linkModemOffset 16 }

		
		-- 1.3.6.1.4.1.16215.1.16.2.8.17
		oduQPSK16Moffset OBJECT-TYPE
			SYNTAX TypeIfModemOffset
			UNITS "Mhz"
			MAX-ACCESS read-write
			STATUS current
			DESCRIPTION
				"If Modem Offset from main signal in case of 16M QPSK in link.
				The Number present 125Khz Multiply
				DEFVAL { 72 }
				InDB = YES
				TypeInDB=CHAR
				ELBIT_PERM(0xFFFFFFFF)
				ADMIN_PERM(0x00000000)
				TECH_PERM(0x00000000)
				USER_PERM(0x00000000)"
			::= { linkModemOffset 17 }

		
		-- 1.3.6.1.4.1.16215.1.16.2.8.18
		oduQPSK34Moffset OBJECT-TYPE
			SYNTAX TypeIfModemOffset
			UNITS "Mhz"
			MAX-ACCESS read-write
			STATUS current
			DESCRIPTION
				"If Modem Offset from main signal in case of 34M QPSK in link.
				The Number present 125Khz Multiply
				DEFVAL { 72 }
				InDB = YES
				TypeInDB=CHAR
				ELBIT_PERM(0xFFFFFFFF)
				ADMIN_PERM(0x00000000)
				TECH_PERM(0x00000000)
				USER_PERM(0x00000000)"
			::= { linkModemOffset 18 }

		
--  1.3.6.1.4.1.16215.1.16.1.7
		-- 1.3.6.1.4.1.16215.1.16.2.9
		status OBJECT IDENTIFIER ::= { odu 9 }

		
		-- 1.3.6.1.4.1.16215.1.16.2.9.1
		oduStsRxLevel OBJECT-TYPE
			SYNTAX OCTET STRING (SIZE (0..255))
			UNITS "Dbm"
			MAX-ACCESS read-only
			STATUS current
			DESCRIPTION
				"Odu Receive Level (Rssi) In Dbm
				InDB = NO"
			::= { status 1 }

		
		-- 1.3.6.1.4.1.16215.1.16.2.9.2
		oduStsTxLevel OBJECT-TYPE
			SYNTAX OCTET STRING (SIZE (0..255))
			UNITS "Dbm"
			MAX-ACCESS read-only
			STATUS current
			DESCRIPTION
				"Odu Transmit Level in Dbm
				InDB = NO"
			::= { status 2 }

		
		-- 1.3.6.1.4.1.16215.1.16.2.9.3
		oduRemStsRxLevel OBJECT-TYPE
			SYNTAX OCTET STRING (SIZE (0..255))
			UNITS "Dbm"
			MAX-ACCESS read-only
			STATUS current
			DESCRIPTION
				"Remote GRX Receive Level (Rssi)In Dbm
				InDB = NO"
			::= { status 3 }

		
		-- 1.3.6.1.4.1.16215.1.16.2.9.4
		oduRemStsBer OBJECT-TYPE
			SYNTAX OCTET STRING (SIZE (0..255))
			MAX-ACCESS read-only
			STATUS current
			DESCRIPTION
				"Remote Link Modem BER status
				InDB = NO"
			::= { status 4 }

		
		-- 1.3.6.1.4.1.16215.1.16.2.9.5
		oduStsVswr OBJECT-TYPE
			SYNTAX OCTET STRING (SIZE (0..255))
			MAX-ACCESS read-only
			STATUS current
			DESCRIPTION
				"Odu Vswr.
				InDB = NO"
			::= { status 5 }

  		-- 1.3.6.1.4.1.16215.1.16.2.9.6
		oduStsVolts5Dot5synt OBJECT-TYPE
			SYNTAX OCTET STRING (SIZE (0..255))
			UNITS "Volts"
			MAX-ACCESS read-only
			STATUS current
			DESCRIPTION
				"Odu 5.5 or 10V synt level status
				InDB = NO"
			::= { status 6 }

   		-- 1.3.6.1.4.1.16215.1.16.2.9.7
		oduStsVolts5V OBJECT-TYPE
			SYNTAX OCTET STRING (SIZE (0..255))
			UNITS "Volts"
			MAX-ACCESS read-only
			STATUS current
			DESCRIPTION
				"Odu 5V level status
				InDB = NO"
			::= { status 7 }


      	-- 1.3.6.1.4.1.16215.1.16.2.9.8
		oduStsVolts8 OBJECT-TYPE
			SYNTAX OCTET STRING (SIZE (0..255))
			UNITS "Volts"
			MAX-ACCESS read-only
			STATUS current
			DESCRIPTION
				"Odu 8V level status
				InDB = NO"
			::= { status 8 }

   		-- 1.3.6.1.4.1.16215.1.16.2.9.9
		oduStsVolts10VPa OBJECT-TYPE
			SYNTAX OCTET STRING (SIZE (0..255))
			UNITS "Volts"
			MAX-ACCESS read-only
			STATUS current
			DESCRIPTION
				"Odu 10V PA level status
				InDB = NO
				"
			::= { status 9 }
        
           
  		-- 1.3.6.1.4.1.16215.1.16.2.9.10
		oduStsVolts3Dot3V OBJECT-TYPE
			SYNTAX OCTET STRING (SIZE (0..255))
			UNITS "Volts"
			MAX-ACCESS read-only
			STATUS current
			DESCRIPTION
				"Odu 3.3v level status
				InDB = NO"
			::= { status 10 }
         
       
       
        -- 1.3.6.1.4.1.16215.1.16.2.9.11
		oduStsVolts6Dot1V OBJECT-TYPE
			SYNTAX OCTET STRING (SIZE (0..255))
			UNITS "Volts"
			MAX-ACCESS read-only
			STATUS current
			DESCRIPTION
				"Odu 6.1v level status
				InDB = NO"
			::= { status 11 }
 
    	-- 1.3.6.1.4.1.16215.1.16.2.9.12
		oduStsVoltsM5 OBJECT-TYPE
			SYNTAX OCTET STRING
			MAX-ACCESS read-only
			STATUS current
			DESCRIPTION
				"Odu -5V level status
				InDB = NO"
			::= { status 12 }
          
          
          -- 1.3.6.1.4.1.16215.1.16.2.9.13
		oduStsVoltsM12 OBJECT-TYPE
			SYNTAX OCTET STRING (SIZE (0..255))
			UNITS "Volts"
			MAX-ACCESS read-only
			STATUS current
			DESCRIPTION
				"Odu -12V level status
				InDB = NO"
			::= { status 13 }

     
        -- 1.3.6.1.4.1.16215.1.16.2.9.14
		oduStsVolts12 OBJECT-TYPE
			SYNTAX OCTET STRING
			MAX-ACCESS read-only
			STATUS current
			DESCRIPTION
				"Odu -12V level status
				InDB = NO"
			::= { status 14 }


   		-- 1.3.6.1.4.1.16215.1.16.2.9.15
		oduStsVolts24VR1Or24VR2 OBJECT-TYPE
			SYNTAX OCTET STRING
			MAX-ACCESS read-only
			STATUS current
			DESCRIPTION
				"24 Volts Ref 1 or 2.
				InDB = NO"
			::= { status 15 }

		
		-- 1.3.6.1.4.1.16215.1.16.2.9.16
		oduStsVolts24VRel1 OBJECT-TYPE
			SYNTAX OCTET STRING (SIZE (0..255))
			UNITS "Volts"
			MAX-ACCESS read-only
			STATUS current
			DESCRIPTION
				"Odu 24V Rel1 level status
				InDB = NO"
			::= { status 16 }

				
		-- 1.3.6.1.4.1.16215.1.16.2.9.17
		oduMainSupplyVoltage OBJECT-TYPE
			SYNTAX OCTET STRING
			MAX-ACCESS read-only
			STATUS current
			DESCRIPTION
				"-48 Volts
				InDB = NO"
			::= { status 17 }

		
		-- 1.3.6.1.4.1.16215.1.16.2.9.18
		oduSWVersion OBJECT-TYPE
			SYNTAX OCTET STRING (SIZE (0..255))
			MAX-ACCESS read-only
			STATUS current
			DESCRIPTION
				"ODU softare & FPGA versions
				InDB = NO"
			::= { status 18 }

		
		-- 1.3.6.1.4.1.16215.1.16.2.9.19
		oduMacAddress OBJECT-TYPE
			SYNTAX OCTET STRING (SIZE (0..255))
			MAX-ACCESS read-only
			STATUS current
			DESCRIPTION
				"ODU MAC address
				InDB = NO"
			::= { status 19 }

		
		-- 1.3.6.1.4.1.16215.1.16.2.9.20
		oduPsTemperature OBJECT-TYPE
			SYNTAX OCTET STRING (SIZE (0..255))
			UNITS "Celsius"
			MAX-ACCESS read-only
			STATUS current
			DESCRIPTION
				"ODU power supplytemperture in Celsius.
				InDB = NO"
			::= { status 20 }

		
		-- 1.3.6.1.4.1.16215.1.16.2.9.21
		oduBit OBJECT-TYPE
			SYNTAX OCTET STRING (SIZE (0..255))
			MAX-ACCESS read-only
			STATUS current
			DESCRIPTION
				"UDU bit status
				InDB = NO"
			::= { status 21 }

		
		-- 1.3.6.1.4.1.16215.1.16.2.9.22
		oduNumber OBJECT-TYPE
			SYNTAX OCTET STRING (SIZE (0..255))
			MAX-ACCESS read-only
			STATUS current
			DESCRIPTION
				"ODU serial number.
				InDB = NO"
			::= { status 22 }

		
		-- 1.3.6.1.4.1.16215.1.16.2.9.23
		oduModem1PreFecBer OBJECT-TYPE
			SYNTAX OCTET STRING (SIZE (0..255))
			MAX-ACCESS read-only
			STATUS current
			DESCRIPTION
				"Odu cable modem Pre ber 
				InDB = NO"
			::= { status 23 }
-- Odu Cable Modem Ber status
		
		-- 1.3.6.1.4.1.16215.1.16.2.9.24
		oduModem1PostFecBer OBJECT-TYPE
			SYNTAX OCTET STRING (SIZE (0..255))
			MAX-ACCESS read-only
			STATUS current
			DESCRIPTION
				"Odu cable modem Post ber 
				InDB = NO"
			::= { status 24 }
-- Odu Cable Modem Ber status
		
		-- 1.3.6.1.4.1.16215.1.16.2.9.25
		oduModem1ModemLock OBJECT-TYPE
			SYNTAX TypeModemLock
			MAX-ACCESS read-only
			STATUS current
			DESCRIPTION
				"Cable Modem Lock state
				InDB = NO"
			::= { status 25 }

		
		-- 1.3.6.1.4.1.16215.1.16.2.9.26
		oduModem1ModemSnr OBJECT-TYPE
			SYNTAX OCTET STRING (SIZE (0..255))
			UNITS "Dbm"
			MAX-ACCESS read-only
			STATUS current
			DESCRIPTION
				"Cable Modem SNr(Signal To Noise ratio) In Dbm
				InDB = NO"
			::= { status 26 }

		
		-- 1.3.6.1.4.1.16215.1.16.2.9.27
		oduModem2PreFecBer OBJECT-TYPE
			SYNTAX OCTET STRING (SIZE (0..255))
			MAX-ACCESS read-only
			STATUS current
			DESCRIPTION
				"Odu link modem Pre ber 
				InDB = NO"
			::= { status 27 }

		
		-- 1.3.6.1.4.1.16215.1.16.2.9.28
		oduModem2PostFecBer OBJECT-TYPE
			SYNTAX OCTET STRING (SIZE (0..255))
			MAX-ACCESS read-only
			STATUS current
			DESCRIPTION
				"Odu link modem Post ber 
				InDB = NO
				
				"
			::= { status 28 }

		
		-- 1.3.6.1.4.1.16215.1.16.2.9.29
		oduModem2ModemLock OBJECT-TYPE
			SYNTAX TypeModemLock
			MAX-ACCESS read-only
			STATUS current
			DESCRIPTION
				"Link Modem Lock state
				InDB = NO"
			::= { status 29 }

		
		-- 1.3.6.1.4.1.16215.1.16.2.9.30
		oduModem2ModemSnr OBJECT-TYPE
			SYNTAX OCTET STRING (SIZE (0..255))
			MAX-ACCESS read-only
			STATUS current
			DESCRIPTION
				"Link Modem SNr(signal to Noise ratio) in Dbm
				InDB = NO"
			::= { status 30 }

		
		-- 1.3.6.1.4.1.16215.1.16.2.9.31
		oduPageSetupStatus OBJECT-TYPE
			SYNTAX TypeStatusuploadCheck
			MAX-ACCESS read-only
			STATUS current
			DESCRIPTION
				"In case of working with page mode the status indicate if the setup is ok (setupOk) otherwise the status 
				will indicate about the first problem that found in the page setup
				InDB = NO"
			::= { status 31 }

		
		-- 1.3.6.1.4.1.16215.1.16.2.9.32
		txsynthesizer1State OBJECT-TYPE
			SYNTAX TypeSynthesizrLock
			MAX-ACCESS read-only
			STATUS current
			DESCRIPTION
				"Status Of TX synthesizer 1 
				InDB = NO
				1 - Synthesizer UnLock
				2 - Synthesizer Lock"
			::= { status 32 }

		
		-- 1.3.6.1.4.1.16215.1.16.2.9.33
		txsynthesizer2State OBJECT-TYPE
			SYNTAX TypeSynthesizrLock
			MAX-ACCESS read-only
			STATUS current
			DESCRIPTION
				"Status Of Tx synthesizer 2
				InDB = NO
				1 - Synthesizer UnLock
				2 - Synthesizer Lock
				Relevenat Only in Hop Mode in fix Mode will be reported as Lock"
			::= { status 33 }

		
		-- 1.3.6.1.4.1.16215.1.16.2.9.34
		rxsynthesizer3State OBJECT-TYPE
			SYNTAX TypeSynthesizrLock
			MAX-ACCESS read-only
			STATUS current
			DESCRIPTION
				"Status Of Rx synthesizer 3
				InDB = NO
				1 - Synthesizer UnLock
				2 - Synthesizer Lock"
			::= { status 34 }

		
		-- 1.3.6.1.4.1.16215.1.16.2.9.35
		rxsynthesizer4State OBJECT-TYPE
			SYNTAX TypeSynthesizrLock
			MAX-ACCESS read-only
			STATUS current
			DESCRIPTION
				"Status Of Rx synthesizer 4
				InDB = NO
				1 - Synthesizer UnLock
				2 - Synthesizer Lock
				Relevenat Only in Hop Mode in fix Mode will be reported as Lock"
			::= { status 35 }

		
		-- 1.3.6.1.4.1.16215.1.16.2.9.36
		fixedsynthesizerState OBJECT-TYPE
			SYNTAX TypeSynthesizrLock
			MAX-ACCESS read-only
			STATUS current
			DESCRIPTION
				"Status Of Fix Ref synthesizer 
				InDB = NO
				1 - Synthesizer UnLock
				2 - Synthesizer Lock"
			::= { status 36 }

		
		-- 1.3.6.1.4.1.16215.1.16.2.9.37
		synthesizerVersion OBJECT-TYPE
			SYNTAX Integer32
			MAX-ACCESS read-only
			STATUS current
			DESCRIPTION
				"sythesizer version
				InDB = NO"
			::= { status 37 }

		
		-- 1.3.6.1.4.1.16215.1.16.2.9.38
		broadcom1FixRssi OBJECT-TYPE
			SYNTAX Integer32
			MAX-ACCESS read-only
			STATUS current
			DESCRIPTION
				"Status Of broadcom Fix 1 RSSI 
				InDB = NO"
			::= { status 38 }

		
		-- 1.3.6.1.4.1.16215.1.16.2.9.39
		broadcom2FixRssi OBJECT-TYPE
			SYNTAX Integer32
			MAX-ACCESS read-only
			STATUS current
			DESCRIPTION
				"Status Of broadcom Fix 2 RSSI
				InDB = NO"
			::= { status 39 }

		
		-- 1.3.6.1.4.1.16215.1.16.2.9.40
		enableDebugPrint OBJECT-TYPE
			SYNTAX TypeOnOff
			MAX-ACCESS read-write
			STATUS current
			DESCRIPTION
				"Enable Print TO terminal APC EVENTS
				InDB = NO"
			::= { status 40 }

		
		-- 1.3.6.1.4.1.16215.1.16.2.9.41
		remoteDeviceRssi OBJECT-TYPE
			SYNTAX OCTET STRING
			MAX-ACCESS read-only
			STATUS current
			DESCRIPTION
				"Remote Link Rssi
				InDB = NO"
			::= { status 41 }

		
		-- 1.3.6.1.4.1.16215.1.16.2.9.42
		remoteModem1PreFecBer OBJECT-TYPE
			SYNTAX OCTET STRING
			MAX-ACCESS read-only
			STATUS current
			DESCRIPTION
				"Remote Link Modem1 Prefec Ber
				InDB = NO"
			::= { status 42 }

		
		-- 1.3.6.1.4.1.16215.1.16.2.9.43
		remoteModem2PreFecBer OBJECT-TYPE
			SYNTAX OCTET STRING
			MAX-ACCESS read-only
			STATUS current
			DESCRIPTION
				"Remote Link Modem2 Prefec Ber
				InDB = NO"
			::= { status 43 }

		
		-- 1.3.6.1.4.1.16215.1.16.2.9.44
		remoteMode1Los OBJECT-TYPE
			SYNTAX TypeOnOff
			MAX-ACCESS read-only
			STATUS current
			DESCRIPTION
				"Remote Link Modem 1 Los
				InDB = NO"
			::= { status 44 }

		
		-- 1.3.6.1.4.1.16215.1.16.2.9.45
		remoteMode2Los OBJECT-TYPE
			SYNTAX TypeOnOff
			MAX-ACCESS read-only
			STATUS current
			DESCRIPTION
				"Remote Link Modem 2 Los
				InDB = NO"
			::= { status 45 }

		
		-- 1.3.6.1.4.1.16215.1.16.2.9.46
		remoteModem1Ber OBJECT-TYPE
			SYNTAX TypeOnOff
			MAX-ACCESS read-only
			STATUS current
			DESCRIPTION
				"Remote Link Modem 1 Ber
				InDB = NO"
			::= { status 46 }

		
		-- 1.3.6.1.4.1.16215.1.16.2.9.47
		remoteModem2Ber OBJECT-TYPE
			SYNTAX TypeOnOff
			MAX-ACCESS read-only
			STATUS current
			DESCRIPTION
				"Remote Link Modem 2 Ber
				InDB = NO"
			::= { status 47 }

		
		-- 1.3.6.1.4.1.16215.1.16.2.9.48
		rfIpCommIsValid OBJECT-TYPE
			SYNTAX TypeOnOff
			MAX-ACCESS read-only
			STATUS current
			DESCRIPTION
				"RF IP communication is ON
				InDB = NO"
			::= { status 48 }

		
		-- 1.3.6.1.4.1.16215.1.16.2.9.49
		powertoChange OBJECT-TYPE
			SYNTAX TypeApcPowerDirection
			MAX-ACCESS read-only
			STATUS current
			DESCRIPTION
				"Power direction Down Up or Idle
				InDB = NO"
			::= { status 49 }

		
		-- 1.3.6.1.4.1.16215.1.16.2.9.50
		oduTempeture OBJECT-TYPE
			SYNTAX OCTET STRING
			MAX-ACCESS read-only
			STATUS current
			DESCRIPTION
				"Odu Temperture
				InDB = NO"
			::= { status 50 }

		
		-- 1.3.6.1.4.1.16215.1.16.2.9.51
		voltage6V OBJECT-TYPE
			SYNTAX OCTET STRING
			MAX-ACCESS read-only
			STATUS current
			DESCRIPTION
				"6v Voltage
				InDB = NO"
			::= { status 51 }

		
		-- 1.3.6.1.4.1.16215.1.16.2.9.52
		voltage1p8V OBJECT-TYPE
			SYNTAX OCTET STRING
			MAX-ACCESS read-only
			STATUS current
			DESCRIPTION
				"Volatage 1.8v
				InDB = NO
				"
			::= { status 52 }

		
		-- 1.3.6.1.4.1.16215.1.16.2.9.53
		voltage1p2V OBJECT-TYPE
			SYNTAX OCTET STRING
			MAX-ACCESS read-only
			STATUS current
			DESCRIPTION
				"Volatage 1.8v
				InDB = NO"
			::= { status 53 }

		
		-- 1.3.6.1.4.1.16215.1.16.2.9.54
		voltage1V OBJECT-TYPE
			SYNTAX OCTET STRING
			MAX-ACCESS read-only
			STATUS current
			DESCRIPTION
				"Volatage 1v
				InDB = NO"
			::= { status 54 }

		
		-- 1.3.6.1.4.1.16215.1.16.2.9.55
		voltage3p3V OBJECT-TYPE
			SYNTAX OCTET STRING
			MAX-ACCESS read-only
			STATUS current
			DESCRIPTION
				"Volatage 3.3v
				InDB = NO"
			::= { status 55 }

		
		-- 1.3.6.1.4.1.16215.1.16.2.9.56
		voltage5V OBJECT-TYPE
			SYNTAX OCTET STRING
			MAX-ACCESS read-only
			STATUS current
			DESCRIPTION
				"Volatage 5v
				InDB = NO"
			::= { status 56 }

		
		-- 1.3.6.1.4.1.16215.1.16.2.9.57
		fpgaVersion OBJECT-TYPE
			SYNTAX OCTET STRING (SIZE (0..255))
			MAX-ACCESS read-only
			STATUS current
			DESCRIPTION
				"FPGA version
				InDB = NO"
			::= { status 57 }

		
		-- 1.3.6.1.4.1.16215.1.16.2.9.58
		vswrValue OBJECT-TYPE
			SYNTAX Integer32 (0..255)
			MAX-ACCESS read-only
			STATUS current
			DESCRIPTION
				"Vswr Value
				InDB = NO"
			::= { status 58 }

		
--  1.3.6.1.4.1.16215.1.16.1.8
		-- 1.3.6.1.4.1.16215.1.16.2.10
		test OBJECT IDENTIFIER ::= { odu 10 }

		
		-- 1.3.6.1.4.1.16215.1.16.2.10.1
		oduTestSetup OBJECT-TYPE
			SYNTAX TypeOnOff
			MAX-ACCESS read-write
			STATUS current
			DESCRIPTION
				"Offline Set Up Parameter Test can be On or OFF
				DEFVAL { 0 }
				InDB = YES
				TypeInDB=UCHAR
				ELBIT_PERM(0x00000003)
				ADMIN_PERM(0x00000000)
				TECH_PERM(0x00000000)
				USER_PERM(0x00000000)"
			::= { test 1 }

		
		-- 1.3.6.1.4.1.16215.1.16.2.10.2
		oduTestFixed OBJECT-TYPE
			SYNTAX TypeOnOff
			MAX-ACCESS read-write
			STATUS current
			DESCRIPTION
				"Offline Fix Parameters Test can be On or OFF
				DEFVAL { 0 }
				InDB = YES
				TypeInDB=UCHAR
				ELBIT_PERM(0x00000003)
				ADMIN_PERM(0x00000000)
				TECH_PERM(0x00000000)
				USER_PERM(0x00000000)"
			::= { test 2 }

		
		-- 1.3.6.1.4.1.16215.1.16.2.10.3
		oduTestLoopBack OBJECT-TYPE
			SYNTAX TypeOnOff
			MAX-ACCESS read-write
			STATUS current
			DESCRIPTION
				"LoopBack On FPGA.
				DEFVAL { 0 }
				InDB = YES
				TypeInDB=UCHAR
				ELBIT_PERM(0x00000003)
				ADMIN_PERM(0x00000000)
				TECH_PERM(0x00000000)
				USER_PERM(0x00000000)"
			::= { test 3 }

		
		-- 1.3.6.1.4.1.16215.1.16.2.10.4
		oduTestLoopBB1 OBJECT-TYPE
			SYNTAX TypeOnOff
			MAX-ACCESS read-write
			STATUS current
			DESCRIPTION
				"Loop BASEBAND 1.
				DEFVAL { 0 }
				InDB = YES
				TypeInDB=UCHAR
				ELBIT_PERM(0x00000003)
				ADMIN_PERM(0x00000000)
				TECH_PERM(0x00000000)
				USER_PERM(0x00000000)"
			::= { test 4 }

		
		-- 1.3.6.1.4.1.16215.1.16.2.10.5
		oduTestBroadCommLoop OBJECT-TYPE
			SYNTAX TypeOnOff
			MAX-ACCESS read-write
			STATUS current
			DESCRIPTION
				"Loop BASEBAND 2.
				DEFVAL { 0 }
				InDB = YES
				TypeInDB=UCHAR
				ELBIT_PERM(0x00000003)
				ADMIN_PERM(0x00000000)
				TECH_PERM(0x00000000)
				USER_PERM(0x00000000)"
			::= { test 5 }

		
		-- 1.3.6.1.4.1.16215.1.16.2.10.6
		oduTestRadioLoop OBJECT-TYPE
			SYNTAX TypeOnOff
			MAX-ACCESS read-write
			STATUS current
			DESCRIPTION
				"RF LOOP
				DEFVAL { 0 }
				InDB = YES
				TypeInDB=UCHAR
				ELBIT_PERM(0x00000003)
				ADMIN_PERM(0x00000000)
				TECH_PERM(0x00000000)
				USER_PERM(0x00000000)"
			::= { test 6 }

		
		-- 1.3.6.1.4.1.16215.1.16.2.10.7
		oduTestAfeLoop OBJECT-TYPE
			SYNTAX TypeOnOff
			MAX-ACCESS read-write
			STATUS current
			DESCRIPTION
				"AFE LOOP
				DEFVAL { 0 }
				InDB = YES
				TypeInDB=UCHAR
				ELBIT_PERM(0x00000003)
				ADMIN_PERM(0x00000000)
				TECH_PERM(0x00000000)
				USER_PERM(0x00000000)"
			::= { test 7 }

		
		-- 1.3.6.1.4.1.16215.1.16.2.10.8
		oduMarvelLoop OBJECT-TYPE
			SYNTAX TypeOnOff
			MAX-ACCESS read-write
			STATUS current
			DESCRIPTION
				"Test Marvel Switch can be On or OFF
				DEFVAL { 0 }
				InDB = YES
				TypeInDB=UCHAR
				ELBIT_PERM(0x00000003)
				ADMIN_PERM(0x00000000)
				TECH_PERM(0x00000000)
				USER_PERM(0x00000000)"
			::= { test 8 }

		-- 1.3.6.1.4.1.16215.1.16.2.10.9
		oduTestFpgaPhyLoop OBJECT-TYPE
			SYNTAX TypeOnOff
			MAX-ACCESS read-write
			STATUS current
			DESCRIPTION
				"Loop BASEBAND 2.
				DEFVAL { 0 }
				InDB = YES
				TypeInDB=UCHAR
				ELBIT_PERM(0x00000003)
				ADMIN_PERM(0x00000000)
				TECH_PERM(0x00000000)
				USER_PERM(0x00000000)"
			::= { test 9 }
		
--  1.3.6.1.4.1.16215.1.16.1.9
		-- 1.3.6.1.4.1.16215.1.16.2.11
		testFaultList OBJECT IDENTIFIER ::= { odu 11 }

		
-- First online test fault 
-- This string includes the first online test faults
		-- 1.3.6.1.4.1.16215.1.16.2.11.1
		oduOnLineTestFault1 OBJECT-TYPE
			SYNTAX OCTET STRING (SIZE (0..255))
			MAX-ACCESS read-only
			STATUS current
			DESCRIPTION
				"First online test fault.
				InDB = NO
				"
			::= { testFaultList 1 }

		
-- Second online test fault 
-- This string includes the second online test faults
		-- 1.3.6.1.4.1.16215.1.16.2.11.2
		oduOnLineTestFault2 OBJECT-TYPE
			SYNTAX OCTET STRING (SIZE (0..255))
			MAX-ACCESS read-only
			STATUS current
			DESCRIPTION
				"Second online test fault.
				InDB = NO"
			::= { testFaultList 2 }

		
-- First offline test fault 
-- This string includes the first offline test faults
		-- 1.3.6.1.4.1.16215.1.16.2.11.3
		oduOffLineTestFault1 OBJECT-TYPE
			SYNTAX OCTET STRING (SIZE (0..255))
			MAX-ACCESS read-only
			STATUS current
			DESCRIPTION
				"First offline test fault.
				InDB = NO"
			::= { testFaultList 3 }

		
-- Second offline test fault 
-- This string includes the second offline test faults
		-- 1.3.6.1.4.1.16215.1.16.2.11.4
		oduOffLineTestFault2 OBJECT-TYPE
			SYNTAX OCTET STRING (SIZE (0..255))
			MAX-ACCESS read-only
			STATUS current
			DESCRIPTION
				"Second offline test fault.
				InDB = NO"
			::= { testFaultList 4 }

		
-- Offline fault test number
		-- 1.3.6.1.4.1.16215.1.16.2.11.5
		oduOffLineTestFaultNbr OBJECT-TYPE
			SYNTAX Integer32 (0..999)
			MAX-ACCESS read-only
			STATUS current
			DESCRIPTION
				"Offline test fault number.
				This number is code for offline test faults
				InDB = NO"
			::= { testFaultList 5 }

		
--  1.3.6.1.4.1.16215.1.16.1.10
		-- 1.3.6.1.4.1.16215.1.16.2.12
		preSelectChannels OBJECT IDENTIFIER ::= { odu 12 }

		
-- Channel(frequency value) need to be activate in PTP mode only
		-- 1.3.6.1.4.1.16215.1.16.2.12.1
		oduSelectChannel OBJECT-TYPE
			SYNTAX TypeSelectChannel
			MAX-ACCESS read-write
			STATUS current
			DESCRIPTION
				"Channel selection.
				DEFVAL { 1 }
				InDB = NO
				ELBIT_PERM(0x000007FE)
				ADMIN_PERM(0x00000000)
				TECH_PERM(0x00000000)
				USER_PERM(0x00000000)"
			::= { preSelectChannels 1 }

		
-- Tx frequency entry 1 in table in case of working with AFC (with channel 6 for RX Frequency) works in PTP only
		-- 1.3.6.1.4.1.16215.1.16.2.12.2
		oduChannelNo1 OBJECT-TYPE
			SYNTAX TypeFrequency
			UNITS "Khz"
			MAX-ACCESS read-write
			STATUS current
			DESCRIPTION
				"Channel 1 (tx Frequncy).
				DEFVAL { 4450000 }
				InDB = YES
				TypeInDB=ULONG
				ELBIT_PERM(0xFFFFFFFF)
				ADMIN_PERM(0x00000000)
				TECH_PERM(0x00000000)
				USER_PERM(0x00000000)"
			::= { preSelectChannels 2 }

		
-- Tx frequency entry 2 in table in case of working with AFC (with channel 7 for RX Frequency) works in PTP only
		-- 1.3.6.1.4.1.16215.1.16.2.12.3
		oduChannelNo2 OBJECT-TYPE
			SYNTAX TypeFrequency
			UNITS "Khz"
			MAX-ACCESS read-write
			STATUS current
			DESCRIPTION
				"Channel 2 (tx Frequncy).
				DEFVAL { 4460000 }
				InDB = YES
				TypeInDB=ULONG
				ELBIT_PERM(0xFFFFFFFF)
				ADMIN_PERM(0x00000000)
				TECH_PERM(0x00000000)
				USER_PERM(0x00000000)"
			::= { preSelectChannels 3 }

		
-- Tx frequency entry 3 in table in case of working with AFC (with channel 8 for RX Frequency) works in PTP only
		-- 1.3.6.1.4.1.16215.1.16.2.12.4
		oduChannelNo3 OBJECT-TYPE
			SYNTAX TypeFrequency
			UNITS "Khz"
			MAX-ACCESS read-write
			STATUS current
			DESCRIPTION
				"Channel 3 (tx Frequncy).
				DEFVAL { 4470000 }
				InDB = YES
				TypeInDB=ULONG
				ELBIT_PERM(0xFFFFFFFF)
				ADMIN_PERM(0x00000000)
				TECH_PERM(0x00000000)
				USER_PERM(0x00000000)"
			::= { preSelectChannels 4 }

		
-- Tx frequency entry 4 in table in case of working with AFC (with channel 9 for RX Frequency) works in PTP only
		-- 1.3.6.1.4.1.16215.1.16.2.12.5
		oduChannelNo4 OBJECT-TYPE
			SYNTAX TypeFrequency
			UNITS "Khz"
			MAX-ACCESS read-write
			STATUS current
			DESCRIPTION
				"Channel 4 (tx Frequncy).
				DEFVAL { 4480000 }
				InDB = YES
				TypeInDB=ULONG
				ELBIT_PERM(0xFFFFFFFF)
				ADMIN_PERM(0x00000000)
				TECH_PERM(0x00000000)
				USER_PERM(0x00000000)"
			::= { preSelectChannels 5 }

		
-- Tx frequency entry 5 in table in case of working with AFC (with channel 10 for RX Frequency) works in PTP only
		-- 1.3.6.1.4.1.16215.1.16.2.12.6
		oduChannelNo5 OBJECT-TYPE
			SYNTAX TypeFrequency
			UNITS "Khz"
			MAX-ACCESS read-write
			STATUS current
			DESCRIPTION
				"Channel 5 (tx Frequncy).
				DEFVAL { 4490000 }
				InDB = YES
				TypeInDB=ULONG
				ELBIT_PERM(0xFFFFFFFF)
				ADMIN_PERM(0x00000000)
				TECH_PERM(0x00000000)
				USER_PERM(0x00000000)"
			::= { preSelectChannels 6 }

		
-- Rx frequency entry 6 in table in case of working with AFC (with channel 1 for TX Frequency) works in PTP only
		-- 1.3.6.1.4.1.16215.1.16.2.12.7
		oduChannelNo6 OBJECT-TYPE
			SYNTAX TypeFrequency
			UNITS "Khz"
			MAX-ACCESS read-write
			STATUS current
			DESCRIPTION
				"Channel 1 (rx Frequncy).
				DEFVAL { 4750000 }
				InDB = YES
				TypeInDB=ULONG
				ELBIT_PERM(0xFFFFFFFF)
				ADMIN_PERM(0x00000000)
				TECH_PERM(0x00000000)
				USER_PERM(0x00000000)"
			::= { preSelectChannels 7 }

		
-- Rx frequency entry 7 in table in case of working with AFC (with channel 2 for TX Frequency) works in PTP only
		-- 1.3.6.1.4.1.16215.1.16.2.12.8
		oduChannelNo7 OBJECT-TYPE
			SYNTAX TypeFrequency
			UNITS "Khz"
			MAX-ACCESS read-write
			STATUS current
			DESCRIPTION
				"Channel 2 (rx Frequncy).
				DEFVAL { 4760000 }
				InDB = YES
				TypeInDB=ULONG
				ELBIT_PERM(0xFFFFFFFF)
				ADMIN_PERM(0x00000000)
				TECH_PERM(0x00000000)
				USER_PERM(0x00000000)"
			::= { preSelectChannels 8 }

		
-- Rx frequency entry 7 in table in case of working with AFC (with channel 3 for TX Frequency) works in PTP only
		-- 1.3.6.1.4.1.16215.1.16.2.12.9
		oduChannelNo8 OBJECT-TYPE
			SYNTAX TypeFrequency
			UNITS "Khz"
			MAX-ACCESS read-write
			STATUS current
			DESCRIPTION
				"Channel 3 (rx Frequncy).
				DEFVAL { 4770000 }
				InDB = YES
				TypeInDB=ULONG
				ELBIT_PERM(0xFFFFFFFF)
				ADMIN_PERM(0x00000000)
				TECH_PERM(0x00000000)
				USER_PERM(0x00000000)"
			::= { preSelectChannels 9 }

		
-- Rx frequency entry 9 in table in case of working with AFC (with channel 4 for TX Frequency) works in PTP only
		-- 1.3.6.1.4.1.16215.1.16.2.12.10
		oduChannelNo9 OBJECT-TYPE
			SYNTAX TypeFrequency
			UNITS "Khz"
			MAX-ACCESS read-write
			STATUS current
			DESCRIPTION
				"Channel 4 (rx Frequncy).
				DEFVAL { 4780000 }
				InDB = YES
				TypeInDB=ULONG
				ELBIT_PERM(0xFFFFFFFF)
				ADMIN_PERM(0x00000000)
				TECH_PERM(0x00000000)
				USER_PERM(0x00000000)"
			::= { preSelectChannels 10 }

		
-- Rx frequency entry 10 in table in case of working with AFC (with channel 5 for TX Frequency) works in PTP only
		-- 1.3.6.1.4.1.16215.1.16.2.12.11
		oduChannelNo10 OBJECT-TYPE
			SYNTAX TypeFrequency
			UNITS "Khz"
			MAX-ACCESS read-write
			STATUS current
			DESCRIPTION
				"Channel 4 (rx Frequncy).
				DEFVAL { 4790000 }
				InDB = YES
				TypeInDB=ULONG
				ELBIT_PERM(0xFFFFFFFF)
				ADMIN_PERM(0x00000000)
				TECH_PERM(0x00000000)
				USER_PERM(0x00000000)"
			::= { preSelectChannels 11 }

		
--  1.3.6.1.4.1.16215.1.16.1.11
		-- 1.3.6.1.4.1.16215.1.16.2.13
		alarms OBJECT IDENTIFIER ::= { odu 13 }

		
-- Wired or for all off possible alarms in GRX8000
		-- 1.3.6.1.4.1.16215.1.16.2.13.1
		oduAlarmGeneral OBJECT-TYPE
			SYNTAX TypeOnOff
			MAX-ACCESS read-only
			STATUS current
			DESCRIPTION
				"General Alarm - if ON means that one of alarms is occured
				InDB = NO"
			::= { alarms 1 }

		
-- RF out alarm in case transmit power level is less from the possible value to it's level
		-- 1.3.6.1.4.1.16215.1.16.2.13.2
		oduAlarmRfOut OBJECT-TYPE
			SYNTAX TypeOnOff
			MAX-ACCESS read-only
			STATUS current
			DESCRIPTION
				"Rf Out Alarm - Power level is below or above limits
				InDB = NO"
			::= { alarms 2 }

		
-- Rf in - receive level is bellow of level that GRX can Handle it.
		-- 1.3.6.1.4.1.16215.1.16.2.13.3
		oduAlarmRfIn OBJECT-TYPE
			SYNTAX TypeOnOff
			MAX-ACCESS read-only
			STATUS current
			DESCRIPTION
				"Rssi Is below limit
				InDB = NO "
			::= { alarms 3 }

		
-- No data (durring to working mode TDM with ETHERNET)
		-- 1.3.6.1.4.1.16215.1.16.2.13.4
		oduAlarmDataOut OBJECT-TYPE
			SYNTAX TypeOnOff
			MAX-ACCESS read-only
			STATUS current
			DESCRIPTION
				"No data in fromFPGA.
				InDB = NO"
			::= { alarms 4 }

		
-- No Data in 
		-- 1.3.6.1.4.1.16215.1.16.2.13.5
		oduAlarmDataIn OBJECT-TYPE
			SYNTAX TypeOnOff
			MAX-ACCESS read-only
			STATUS current
			DESCRIPTION
				"No data in from switch
				InDB = NO"
			::= { alarms 5 }

		
-- Cable Modem LOS alarm
		-- 1.3.6.1.4.1.16215.1.16.2.13.6
		oduModem1AlarmLos OBJECT-TYPE
			SYNTAX TypeOnOff
			MAX-ACCESS read-only
			STATUS current
			DESCRIPTION
				"Cable modem Loas alarm.
				InDB = NO"
			::= { alarms 6 }

		
-- Cable Modem BER alarm
		-- 1.3.6.1.4.1.16215.1.16.2.13.7
		oduModem1AlarmBer OBJECT-TYPE
			SYNTAX TypeOnOff
			MAX-ACCESS read-only
			STATUS current
			DESCRIPTION
				"Cable modem Ber alarm
				InDB = NO"
			::= { alarms 7 }

		
-- Link Modem LOS alarm
		-- 1.3.6.1.4.1.16215.1.16.2.13.8
		oduModem2AlarmLos OBJECT-TYPE
			SYNTAX TypeOnOff
			MAX-ACCESS read-only
			STATUS current
			DESCRIPTION
				"Link modem Los alarm
				InDB = NO"
			::= { alarms 8 }

		
-- Link Modem BER alarm
		-- 1.3.6.1.4.1.16215.1.16.2.13.9
		oduModem2AlarmBer OBJECT-TYPE
			SYNTAX TypeOnOff
			MAX-ACCESS read-only
			STATUS current
			DESCRIPTION
				"Link Modem Ber alarm
				InDB = NO"
			::= { alarms 9 }

		
		-- 1.3.6.1.4.1.16215.1.16.2.13.10
		vswrAlarm OBJECT-TYPE
			SYNTAX TypeVswrOkNotOk
			MAX-ACCESS read-only
			STATUS current
			DESCRIPTION
				"Vswr Alarm state
				InDB = NO"
			::= { alarms 10 }
			
			
			
			-- 1.3.6.1.4.1.16215.1.16.2.13.11
		hopRfLoop OBJECT-TYPE
			SYNTAX TypeOnOff
			MAX-ACCESS read-only
			STATUS current
			DESCRIPTION
				"0 - Alarm OFF
				1 - Alarm ON"
			::= { alarms 11 }

		-- 1.3.6.1.4.1.16215.1.16.2.13.12
		hopAfeLoop OBJECT-TYPE
			SYNTAX TypeOnOff
			MAX-ACCESS read-only
			STATUS current
			DESCRIPTION
				"0 - Alarm OFF
				1 - Alarm ON"
			::= { alarms 12 }

		-- 1.3.6.1.4.1.16215.1.16.2.13.13
		hopFpgaPhyLoop OBJECT-TYPE
			SYNTAX TypeOnOff
			MAX-ACCESS read-only
			STATUS current
			DESCRIPTION
				"0 - Alarm OFF
				1 - Alarm ON"
			::= { alarms 13 }  
			
		-- 1.3.6.1.4.1.16215.1.16.2.13.14
		hopPerLink1 OBJECT-TYPE
			SYNTAX TypeOnOff
			MAX-ACCESS read-only
			STATUS current
			DESCRIPTION
				"0 - Alarm OFF
				1 - Alarm ON"
			::= { alarms 14 } 

		-- 1.3.6.1.4.1.16215.1.16.2.13.15
		hopPerLink2 OBJECT-TYPE
			SYNTAX TypeOnOff
			MAX-ACCESS read-only
			STATUS current
			DESCRIPTION
				"0 - Alarm OFF
				1 - Alarm ON"
			::= { alarms 15 }

		-- 1.3.6.1.4.1.16215.1.16.2.13.16
		hopPerLink3 OBJECT-TYPE
			SYNTAX TypeOnOff
			MAX-ACCESS read-only
			STATUS current
			DESCRIPTION
				"0 - Alarm OFF
				1 - Alarm ON"
			::= { alarms 16 }
              
		-- 1.3.6.1.4.1.16215.1.16.2.13.17
		hopSnrLink1 OBJECT-TYPE
			SYNTAX TypeOnOff
			MAX-ACCESS read-only
			STATUS current
			DESCRIPTION
				"0 - Alarm OFF
				1 - Alarm ON"
			::= { alarms 17 } 

		-- 1.3.6.1.4.1.16215.1.16.2.13.18
		hopSnrLink2 OBJECT-TYPE
			SYNTAX TypeOnOff
			MAX-ACCESS read-only
			STATUS current
			DESCRIPTION
				"0 - Alarm OFF
				1 - Alarm ON"
			::= { alarms 18 }

		-- 1.3.6.1.4.1.16215.1.16.2.13.19
		hopSnrLink3 OBJECT-TYPE
			SYNTAX TypeOnOff
			MAX-ACCESS read-only
			STATUS current
			DESCRIPTION
				"0 - Alarm OFF
				1 - Alarm ON"
			::= { alarms 19 }

		-- 1.3.6.1.4.1.16215.1.16.2.13.20
		hopNP OBJECT-TYPE
			SYNTAX TypeOnOff
			MAX-ACCESS read-only
			STATUS current
			DESCRIPTION
				"0 - Alarm OFF
				1 - Alarm ON"
			::= { alarms 20 }

            trapNotificationTest NOTIFICATION-TYPE
			OBJECTS { hopFpgaPhyLoop }
			STATUS current
			DESCRIPTION 
				"Send Notification to manager."
			::= { alarms 21 }

		
--  1.3.6.1.4.1.16215.1.16.1.12
		-- 1.3.6.1.4.1.16215.1.16.2.14
		broadcom OBJECT IDENTIFIER ::= { odu 14 }

		
-- Cable modem. Address of BCM6020 register
		-- 1.3.6.1.4.1.16215.1.16.2.14.1
		oduModem1AddressOfBCM6020Reg OBJECT-TYPE
			SYNTAX INTEGER (0..65535)
			MAX-ACCESS read-write
			STATUS current
			DESCRIPTION
				"Cable modem register address
				InDB = NO"
			::= { broadcom 1 }

		
-- Cable modem. Single or Multy register
		-- 1.3.6.1.4.1.16215.1.16.2.14.2
		oduModem1SingleMultyOfBCM6020Reg OBJECT-TYPE
			SYNTAX TypeModemAction
			MAX-ACCESS read-write
			STATUS current
			DESCRIPTION
				"Cable modem function required
				InDB = NO"
			::= { broadcom 2 }

		
-- Cable modem. L.S.B. Value of BCM6020 register
		-- 1.3.6.1.4.1.16215.1.16.2.14.3
		oduModem1ValueOfBCM6020Reg1 OBJECT-TYPE
			SYNTAX Integer32
			MAX-ACCESS read-write
			STATUS current
			DESCRIPTION
				"Cable modem register Value(LSB)
				InDB = NO"
			::= { broadcom 3 }

		
-- Cable modem. M.S.B. Value of BCM6020 register
		-- 1.3.6.1.4.1.16215.1.16.2.14.4
		oduModem1ValueOfBCM6020Reg2 OBJECT-TYPE
			SYNTAX Integer32
			MAX-ACCESS read-write
			STATUS current
			DESCRIPTION
				"Cable modem register Value(MSB)
				InDB = NO"
			::= { broadcom 4 }

		
-- Link modem. Address of BCM6020 register
		-- 1.3.6.1.4.1.16215.1.16.2.14.5
		oduModem2AddressOfBCM6020Reg OBJECT-TYPE
			SYNTAX INTEGER (0..65535)
			MAX-ACCESS read-write
			STATUS current
			DESCRIPTION
				"Link modem register address
				InDB = NO"
			::= { broadcom 5 }

		
-- Link modem. Single or Multy register
		-- 1.3.6.1.4.1.16215.1.16.2.14.6
		oduModem2SingleMultyOfBCM6020Reg OBJECT-TYPE
			SYNTAX TypeModemAction
			MAX-ACCESS read-write
			STATUS current
			DESCRIPTION
				"Link modem function required
				InDB = NO"
			::= { broadcom 6 }

		
-- Link modem. L.S.B. Value of BCM6020 register
		-- 1.3.6.1.4.1.16215.1.16.2.14.7
		oduModem2ValueOfBCM6020Reg1 OBJECT-TYPE
			SYNTAX Integer32
			MAX-ACCESS read-write
			STATUS current
			DESCRIPTION
				"Link modem register Value(LSB)
				InDB = NO"
			::= { broadcom 7 }

		
-- Link modem. M.S.B. Value of BCM6020 register
		-- 1.3.6.1.4.1.16215.1.16.2.14.8
		oduModem2ValueOfBCM6020Reg2 OBJECT-TYPE
			SYNTAX Integer32
			MAX-ACCESS read-write
			STATUS current
			DESCRIPTION
				"Link modem register Value(MSB)
				InDB = NO"
			::= { broadcom 8 }

		
--  1.3.6.1.4.1.16215.1.16.1.13
		-- 1.3.6.1.4.1.16215.1.16.2.15
		apcParams OBJECT IDENTIFIER ::= { odu 15 }

		
		-- 1.3.6.1.4.1.16215.1.16.2.15.1
		timerT11 OBJECT-TYPE
			SYNTAX INTEGER (3..20)
			UNITS "Sec"
			MAX-ACCESS read-write
			STATUS current
			DESCRIPTION
				"Apc Timer T11
				DEFVAL { 3 }
				InDB = YES
				TypeInDB=UCHAR
				ELBIT_PERM(0xFFFFFFFF)
				ADMIN_PERM(0x00000000)
				TECH_PERM(0x00000000)
				USER_PERM(0x00000000)"
			::= { apcParams 1 }

		
		-- 1.3.6.1.4.1.16215.1.16.2.15.2
		timerT12 OBJECT-TYPE
			SYNTAX INTEGER (3..20)
			UNITS "Sec"
			MAX-ACCESS read-write
			STATUS current
			DESCRIPTION
				"Apc Timer T12
				DEFVAL { 4 }
				InDB = YES
				TypeInDB=UCHAR
				ELBIT_PERM(0xFFFFFFFF)
				ADMIN_PERM(0x00000000)
				TECH_PERM(0x00000000)
				USER_PERM(0x00000000)"
			::= { apcParams 2 }

		
		-- 1.3.6.1.4.1.16215.1.16.2.15.3
		timerT13 OBJECT-TYPE
			SYNTAX INTEGER (3..20)
			UNITS "Sec"
			MAX-ACCESS read-write
			STATUS current
			DESCRIPTION
				"Apc Timer T13
				DEFVAL { 5 }
				InDB = YES
				TypeInDB=UCHAR
				ELBIT_PERM(0xFFFFFFFF)
				ADMIN_PERM(0x00000000)
				TECH_PERM(0x00000000)
				USER_PERM(0x00000000)"
			::= { apcParams 3 }

		
		-- 1.3.6.1.4.1.16215.1.16.2.15.4
		timerT14 OBJECT-TYPE
			SYNTAX INTEGER (3..20)
			UNITS "Sec"
			MAX-ACCESS read-write
			STATUS current
			DESCRIPTION
				"Apc Timer T14
				DEFVAL { 7 }
				InDB = YES
				TypeInDB=UCHAR
				ELBIT_PERM(0xFFFFFFFF)
				ADMIN_PERM(0x00000000)
				TECH_PERM(0x00000000)
				USER_PERM(0x00000000)"
			::= { apcParams 4 }

		
		-- 1.3.6.1.4.1.16215.1.16.2.15.5
		deltaP OBJECT-TYPE
			SYNTAX TypeDeltaPower
			MAX-ACCESS read-write
			STATUS current
			DESCRIPTION
				"Delta Power increase step in Dbm
				DEFVAL { 1 }
				InDB = YES
				TypeInDB=INT
				ELBIT_PERM(0xFFFFFFFF)
				ADMIN_PERM(0x00000000)
				TECH_PERM(0x00000000)
				USER_PERM(0x00000000)"
			::= { apcParams 5 }

		
		-- 1.3.6.1.4.1.16215.1.16.2.15.6
		deltaN OBJECT-TYPE
			SYNTAX TypeDeltaPower
			MAX-ACCESS read-write
			STATUS current
			DESCRIPTION
				"Delta Power decrease step in Dbm
				DEFVAL { 1 }
				InDB = YES
				TypeInDB=INT
				ELBIT_PERM(0xFFFFFFFF)
				ADMIN_PERM(0x00000000)
				TECH_PERM(0x00000000)
				USER_PERM(0x00000000)"
			::= { apcParams 6 }

		
-- Maximum Transmit power level to QPSK modulation
		-- 1.3.6.1.4.1.16215.1.16.2.15.7
		pTXmaxQPSK OBJECT-TYPE
			SYNTAX TypeMaxPower
			UNITS "Dbm"
			MAX-ACCESS read-write
			STATUS current
			DESCRIPTION
				"Mximum Transmit Power level in QPSK
				DEFVAL { 34 }
				InDB = YES
				TypeInDB=UCHAR
				ELBIT_PERM(0xFFFFFFFF)
				ADMIN_PERM(0x00000000)
				TECH_PERM(0x00000000)
				USER_PERM(0x00000000)
				"
			::= { apcParams 7 }

		
-- Maximum Transmit power level to 16QAM modulation
		-- 1.3.6.1.4.1.16215.1.16.2.15.8
		pTXmax16QAM OBJECT-TYPE
			SYNTAX TypeMaxPower
			UNITS "Dbm"
			MAX-ACCESS read-write
			STATUS current
			DESCRIPTION
				"Mximum Transmit Power level in 16QAM
				DEFVAL { 32 }
				InDB = YES
				TypeInDB=UCHAR
				ELBIT_PERM(0xFFFFFFFF)
				ADMIN_PERM(0x00000000)
				TECH_PERM(0x00000000)
				USER_PERM(0x00000000)
				"
			::= { apcParams 8 }

		
-- Maximum Transmit power level to 64QAM modulation
		-- 1.3.6.1.4.1.16215.1.16.2.15.9
		pTXmax64QAM OBJECT-TYPE
			SYNTAX TypeMaxPower
			UNITS "Dbm"
			MAX-ACCESS read-write
			STATUS current
			DESCRIPTION
				"Mximum Transmit Power level in 64QAM
				DEFVAL { 29 }
				InDB = YES
				TypeInDB=UCHAR
				ELBIT_PERM(0xFFFFFFFF)
				ADMIN_PERM(0x00000000)
				TECH_PERM(0x00000000)
				USER_PERM(0x00000000)
				"
			::= { apcParams 9 }

		
--  1.3.6.1.4.1.16215.1.16.1.14
		-- 1.3.6.1.4.1.16215.1.16.2.16
		apcThreshold OBJECT IDENTIFIER ::= { odu 16 }

		
		-- 1.3.6.1.4.1.16215.1.16.2.16.1
		ptp OBJECT IDENTIFIER ::= { apcThreshold 1 }

		
		-- 1.3.6.1.4.1.16215.1.16.2.16.1.1
		ptp64QAM OBJECT IDENTIFIER ::= { ptp 1 }

		
		-- 1.3.6.1.4.1.16215.1.16.2.16.1.1.1
		ptppreBERmax8M64QAM OBJECT-TYPE
			SYNTAX TypePrefecBer
			MAX-ACCESS read-write
			STATUS current
			DESCRIPTION
				"PTP preBERmax for 8M 64QAM
				DEFVAL { 1E-6 }
				InDB = YES
				TypeInDB=FLOAT
				ELBIT_PERM(0xFFFFFFFF)
				ADMIN_PERM(0x00000000)
				TECH_PERM(0x00000000)
				USER_PERM(0x00000000)"
			::= { ptp64QAM 1 }

		
		-- 1.3.6.1.4.1.16215.1.16.2.16.1.1.2
		ptprSSImin8M64QAM OBJECT-TYPE
			SYNTAX TypeRssiValue
			MAX-ACCESS read-write
			STATUS current
			DESCRIPTION
				"PTP rSSImin for 8M 64QAM
				DEFVAL { -69 }
				InDB = YES
				TypeInDB=INT
				ELBIT_PERM(0xFFFFFFFF)
				ADMIN_PERM(0x00000000)
				TECH_PERM(0x00000000)
				USER_PERM(0x00000000)"
			::= { ptp64QAM 2 }

		
		-- 1.3.6.1.4.1.16215.1.16.2.16.1.1.3
		ptprSSImax8M64QAM OBJECT-TYPE
			SYNTAX TypeRssiValue
			MAX-ACCESS read-write
			STATUS current
			DESCRIPTION
				"PTP rSSImax for 8M 64QAM
				DEFVAL { -64 }
				InDB = YES
				TypeInDB=INT
				ELBIT_PERM(0xFFFFFFFF)
				ADMIN_PERM(0x00000000)
				TECH_PERM(0x00000000)
				USER_PERM(0x00000000)"
			::= { ptp64QAM 3 }

		
		-- 1.3.6.1.4.1.16215.1.16.2.16.1.1.4
		ptppreBERmax16M64QAM OBJECT-TYPE
			SYNTAX TypePrefecBer
			MAX-ACCESS read-write
			STATUS current
			DESCRIPTION
				"PTP preBERmax for 16M 64QAM
				DEFVAL { 1E-6 }
				InDB = YES
				TypeInDB=FLOAT
				ELBIT_PERM(0xFFFFFFFF)
				ADMIN_PERM(0x00000000)
				TECH_PERM(0x00000000)
				USER_PERM(0x00000000)"
			::= { ptp64QAM 4 }

		
		-- 1.3.6.1.4.1.16215.1.16.2.16.1.1.5
		ptprSSImin16M64QAM OBJECT-TYPE
			SYNTAX TypeRssiValue
			UNITS "Dbm"
			MAX-ACCESS read-write
			STATUS current
			DESCRIPTION
				"PTP rSSImin for 16M 64QAM
				DEFVAL { -69 }
				InDB = YES
				TypeInDB=INT
				ELBIT_PERM(0xFFFFFFFF)
				ADMIN_PERM(0x00000000)
				TECH_PERM(0x00000000)
				USER_PERM(0x00000000)
				"
			::= { ptp64QAM 5 }

		
		-- 1.3.6.1.4.1.16215.1.16.2.16.1.1.6
		ptprSSImax16M64QAM OBJECT-TYPE
			SYNTAX TypeRssiValue
			UNITS "Dbm"
			MAX-ACCESS read-write
			STATUS current
			DESCRIPTION
				"PTP rSSImax for 16M 64QAM
				DEFVAL { -64 }
				InDB = YES
				TypeInDB=INT
				ELBIT_PERM(0xFFFFFFFF)
				ADMIN_PERM(0x00000000)
				TECH_PERM(0x00000000)
				USER_PERM(0x00000000)
				"
			::= { ptp64QAM 6 }

		
		-- 1.3.6.1.4.1.16215.1.16.2.16.1.1.7
		ptppreBERmax34M64QAM OBJECT-TYPE
			SYNTAX TypePrefecBer
			MAX-ACCESS read-write
			STATUS current
			DESCRIPTION
				"PTP preBERmax for 34M 64QAM
				DEFVAL { 1E-6 }
				InDB = YES
				TypeInDB=FLOAT
				ELBIT_PERM(0xFFFFFFFF)
				ADMIN_PERM(0x00000000)
				TECH_PERM(0x00000000)
				USER_PERM(0x00000000)"
			::= { ptp64QAM 7 }

		
		-- 1.3.6.1.4.1.16215.1.16.2.16.1.1.8
		ptprSSImin34M64QAM OBJECT-TYPE
			SYNTAX TypeRssiValue
			UNITS "Dbm"
			MAX-ACCESS read-write
			STATUS current
			DESCRIPTION
				"PTP rSSImin for 34M 64QAM
				DEFVAL { -66 }
				InDB = YES
				TypeInDB=INT
				ELBIT_PERM(0xFFFFFFFF)
				ADMIN_PERM(0x00000000)
				TECH_PERM(0x00000000)
				USER_PERM(0x00000000)
				"
			::= { ptp64QAM 8 }

		
		-- 1.3.6.1.4.1.16215.1.16.2.16.1.1.9
		ptprSSImax34M64QAM OBJECT-TYPE
			SYNTAX TypeRssiValue
			UNITS "Dbm"
			MAX-ACCESS read-write
			STATUS current
			DESCRIPTION
				"PTP rSSImax for 34M 64QAM
				DEFVAL { -61 }
				InDB = YES
				TypeInDB=INT
				ELBIT_PERM(0xFFFFFFFF)
				ADMIN_PERM(0x00000000)
				TECH_PERM(0x00000000)
				USER_PERM(0x00000000)
				"
			::= { ptp64QAM 9 }

		
		-- 1.3.6.1.4.1.16215.1.16.2.16.1.1.10
		ptppreBERmax52M64QAM OBJECT-TYPE
			SYNTAX TypePrefecBer
			MAX-ACCESS read-write
			STATUS current
			DESCRIPTION
				"PTP preBERmax for 52M 64QAM
				DEFVAL { 1E-5 }
				InDB = YES
				TypeInDB=FLOAT
				ELBIT_PERM(0xFFFFFFFF)
				ADMIN_PERM(0x00000000)
				TECH_PERM(0x00000000)
				USER_PERM(0x00000000)"
			::= { ptp64QAM 10 }

		
		-- 1.3.6.1.4.1.16215.1.16.2.16.1.1.11
		ptprSSImin52M64QAM OBJECT-TYPE
			SYNTAX TypeRssiValue
			UNITS "Dbm"
			MAX-ACCESS read-write
			STATUS current
			DESCRIPTION
				"PTP rSSImin for 52M 64QAM
				DEFVAL { -64 }
				InDB = YES
				TypeInDB=INT
				ELBIT_PERM(0xFFFFFFFF)
				ADMIN_PERM(0x00000000)
				TECH_PERM(0x00000000)
				USER_PERM(0x00000000)
				"
			::= { ptp64QAM 11 }

		
		-- 1.3.6.1.4.1.16215.1.16.2.16.1.1.12
		ptprSSImax52M64QAM OBJECT-TYPE
			SYNTAX TypeRssiValue
			UNITS "Dbm"
			MAX-ACCESS read-write
			STATUS current
			DESCRIPTION
				"PTP rSSImax for 52M 64QAM
				DEFVAL { -59 }
				InDB = YES
				TypeInDB=INT
				ELBIT_PERM(0xFFFFFFFF)
				ADMIN_PERM(0x00000000)
				TECH_PERM(0x00000000)
				USER_PERM(0x00000000)
				"
			::= { ptp64QAM 12 }

		
		-- 1.3.6.1.4.1.16215.1.16.2.16.1.1.13
		ptppreBERmax104M64QAM OBJECT-TYPE
			SYNTAX TypePrefecBer
			MAX-ACCESS read-write
			STATUS current
			DESCRIPTION
				"PTP preBERmax for 104M 64QAM
				DEFVAL { 1E-5 }
				InDB = YES
				TypeInDB=FLOAT
				ELBIT_PERM(0xFFFFFFFF)
				ADMIN_PERM(0x00000000)
				TECH_PERM(0x00000000)
				USER_PERM(0x00000000)"
			::= { ptp64QAM 13 }

		
		-- 1.3.6.1.4.1.16215.1.16.2.16.1.1.14
		ptprSSImin104M64QAM OBJECT-TYPE
			SYNTAX TypeRssiValue
			UNITS "Dbm"
			MAX-ACCESS read-write
			STATUS current
			DESCRIPTION
				"PTP rSSImin for 104M 64QAM
				DEFVAL { -65 }
				InDB = YES
				TypeInDB=INT
				ELBIT_PERM(0xFFFFFFFF)
				ADMIN_PERM(0x00000000)
				TECH_PERM(0x00000000)
				USER_PERM(0x00000000)
				"
			::= { ptp64QAM 14 }

		
		-- 1.3.6.1.4.1.16215.1.16.2.16.1.1.15
		ptprSSImax104M64QAM OBJECT-TYPE
			SYNTAX TypeRssiValue
			UNITS "Dbm"
			MAX-ACCESS read-write
			STATUS current
			DESCRIPTION
				"PTP rSSImax for 104M 64QAM.
				DEFVAL { -55 }
				InDB = YES
				TypeInDB=INT
				ELBIT_PERM(0xFFFFFFFF)
				ADMIN_PERM(0x00000000)
				TECH_PERM(0x00000000)
				USER_PERM(0x00000000)
				"
			::= { ptp64QAM 15 }

		
		-- 1.3.6.1.4.1.16215.1.16.2.16.1.2
		ptp16QAM OBJECT IDENTIFIER ::= { ptp 2 }

		
		-- 1.3.6.1.4.1.16215.1.16.2.16.1.2.1
		ptppreBERmax2M16QAM OBJECT-TYPE
			SYNTAX TypePrefecBer
			MAX-ACCESS read-write
			STATUS current
			DESCRIPTION
				"PTP preBERmax for 2M 16QAM
				DEFVAL { 1E-6 }
				InDB = YES
				TypeInDB=FLOAT
				ELBIT_PERM(0xFFFFFFFF)
				ADMIN_PERM(0x00000000)
				TECH_PERM(0x00000000)
				USER_PERM(0x00000000)"
			::= { ptp16QAM 1 }

		
		-- 1.3.6.1.4.1.16215.1.16.2.16.1.2.2
		ptprSSImin2M16QAM OBJECT-TYPE
			SYNTAX TypeRssiValue
			UNITS "Dbm"
			MAX-ACCESS read-write
			STATUS current
			DESCRIPTION
				"PTP rSSImin for 2M 16QAM
				DEFVAL { -92 }
				InDB = YES
				TypeInDB=INT
				ELBIT_PERM(0xFFFFFFFF)
				ADMIN_PERM(0x00000000)
				TECH_PERM(0x00000000)
				USER_PERM(0x00000000)
				"
			::= { ptp16QAM 2 }

		
		-- 1.3.6.1.4.1.16215.1.16.2.16.1.2.3
		ptprSSImax2M16QAM OBJECT-TYPE
			SYNTAX TypeRssiValue
			UNITS "Dbm"
			MAX-ACCESS read-write
			STATUS current
			DESCRIPTION
				"PTP rSSImax for 2M 16QAM
				DEFVAL { -87 }
				InDB = YES
				TypeInDB=INT
				ELBIT_PERM(0xFFFFFFFF)
				ADMIN_PERM(0x00000000)
				TECH_PERM(0x00000000)
				USER_PERM(0x00000000)
				"
			::= { ptp16QAM 3 }

		
		-- 1.3.6.1.4.1.16215.1.16.2.16.1.2.4
		ptppreBERmax4M16QAM OBJECT-TYPE
			SYNTAX TypePrefecBer
			MAX-ACCESS read-write
			STATUS current
			DESCRIPTION
				"PTP preBERmax for 4M 16QAM
				DEFVAL { 1E-6 }
				InDB = YES
				TypeInDB=FLOAT
				ELBIT_PERM(0xFFFFFFFF)
				ADMIN_PERM(0x00000000)
				TECH_PERM(0x00000000)
				USER_PERM(0x00000000)"
			::= { ptp16QAM 4 }

		
		-- 1.3.6.1.4.1.16215.1.16.2.16.1.2.5
		ptprSSImin4M16QAM OBJECT-TYPE
			SYNTAX TypeRssiValue
			UNITS "Dbm"
			MAX-ACCESS read-write
			STATUS current
			DESCRIPTION
				"PTP rSSImin for 4M 16QAM
				DEFVAL { -82 }
				InDB = YES
				TypeInDB=INT
				ELBIT_PERM(0xFFFFFFFF)
				ADMIN_PERM(0x00000000)
				TECH_PERM(0x00000000)
				USER_PERM(0x00000000)
				"
			::= { ptp16QAM 5 }

		
		-- 1.3.6.1.4.1.16215.1.16.2.16.1.2.6
		ptprSSImax4M16QAM OBJECT-TYPE
			SYNTAX TypeRssiValue
			UNITS "Dbm"
			MAX-ACCESS read-write
			STATUS current
			DESCRIPTION
				"PTP rSSImax for 4M 16QAM
				DEFVAL { -77 }
				InDB = YES
				TypeInDB=INT
				ELBIT_PERM(0xFFFFFFFF)
				ADMIN_PERM(0x00000000)
				TECH_PERM(0x00000000)
				USER_PERM(0x00000000)
				"
			::= { ptp16QAM 6 }

		
		-- 1.3.6.1.4.1.16215.1.16.2.16.1.2.7
		ptppreBERmax8M16QAM OBJECT-TYPE
			SYNTAX TypePrefecBer
			MAX-ACCESS read-write
			STATUS current
			DESCRIPTION
				"PTP preBERmax for 8M 16QAM
				DEFVAL { 1E-6 }
				InDB = YES
				TypeInDB=FLOAT
				ELBIT_PERM(0xFFFFFFFF)
				ADMIN_PERM(0x00000000)
				TECH_PERM(0x00000000)
				USER_PERM(0x00000000)"
			::= { ptp16QAM 7 }

		
		-- 1.3.6.1.4.1.16215.1.16.2.16.1.2.8
		ptprSSImin8M16QAM OBJECT-TYPE
			SYNTAX TypeRssiValue
			UNITS "Dbm"
			MAX-ACCESS read-write
			STATUS current
			DESCRIPTION
				"PTP rSSImin for 8M 16QAM
				DEFVAL { -79 }
				InDB = YES
				TypeInDB=INT
				ELBIT_PERM(0xFFFFFFFF)
				ADMIN_PERM(0x00000000)
				TECH_PERM(0x00000000)
				USER_PERM(0x00000000)
				"
			::= { ptp16QAM 8 }

		
		-- 1.3.6.1.4.1.16215.1.16.2.16.1.2.9
		ptprSSImax8M16QAM OBJECT-TYPE
			SYNTAX TypeRssiValue
			UNITS "Dbm"
			MAX-ACCESS read-write
			STATUS current
			DESCRIPTION
				"PTP rSSImax for 8M 16QAM
				DEFVAL { -74 }
				InDB = YES
				TypeInDB=INT
				ELBIT_PERM(0xFFFFFFFF)
				ADMIN_PERM(0x00000000)
				TECH_PERM(0x00000000)
				USER_PERM(0x00000000)
				"
			::= { ptp16QAM 9 }

		
		-- 1.3.6.1.4.1.16215.1.16.2.16.1.2.10
		ptppreBERmax16M16QAM OBJECT-TYPE
			SYNTAX TypePrefecBer
			MAX-ACCESS read-write
			STATUS current
			DESCRIPTION
				"PTP preBERmax for 16M 16QAM
				DEFVAL { 1E-6 }
				InDB = YES
				TypeInDB=FLOAT
				ELBIT_PERM(0xFFFFFFFF)
				ADMIN_PERM(0x00000000)
				TECH_PERM(0x00000000)
				USER_PERM(0x00000000)"
			::= { ptp16QAM 10 }

		
		-- 1.3.6.1.4.1.16215.1.16.2.16.1.2.11
		ptprSSImin16M16QAM OBJECT-TYPE
			SYNTAX TypeRssiValue
			UNITS "Dbm"
			MAX-ACCESS read-write
			STATUS current
			DESCRIPTION
				"PTP rSSImin for 16M 16QAM
				DEFVAL { -75 }
				InDB = YES
				TypeInDB=INT
				ELBIT_PERM(0xFFFFFFFF)
				ADMIN_PERM(0x00000000)
				TECH_PERM(0x00000000)
				USER_PERM(0x00000000)
				"
			::= { ptp16QAM 11 }

		
		-- 1.3.6.1.4.1.16215.1.16.2.16.1.2.12
		ptprSSImax16M16QAM OBJECT-TYPE
			SYNTAX TypeRssiValue
			UNITS "Dbm"
			MAX-ACCESS read-write
			STATUS current
			DESCRIPTION
				"PTP rSSImax for 16M 16QAM
				DEFVAL { -71 }
				InDB = YES
				TypeInDB=INT
				ELBIT_PERM(0xFFFFFFFF)
				ADMIN_PERM(0x00000000)
				TECH_PERM(0x00000000)
				USER_PERM(0x00000000)
				"
			::= { ptp16QAM 12 }

		
		-- 1.3.6.1.4.1.16215.1.16.2.16.1.2.13
		ptppreBERmax34M16QAM OBJECT-TYPE
			SYNTAX TypePrefecBer
			MAX-ACCESS read-write
			STATUS current
			DESCRIPTION
				"PTP preBERmax for 34M 16QAM
				DEFVAL { 1E-6 }
				InDB = YES
				TypeInDB=FLOAT
				ELBIT_PERM(0xFFFFFFFF)
				ADMIN_PERM(0x00000000)
				TECH_PERM(0x00000000)
				USER_PERM(0x00000000)"
			::= { ptp16QAM 13 }

		
		-- 1.3.6.1.4.1.16215.1.16.2.16.1.2.14
		ptprSSImin34M16QAM OBJECT-TYPE
			SYNTAX TypeRssiValue
			UNITS "Dbm"
			MAX-ACCESS read-write
			STATUS current
			DESCRIPTION
				"PTP rSSImin for 34M 16QAM
				DEFVAL { -73 }
				InDB = YES
				TypeInDB=INT
				ELBIT_PERM(0xFFFFFFFF)
				ADMIN_PERM(0x00000000)
				TECH_PERM(0x00000000)
				USER_PERM(0x00000000)
				"
			::= { ptp16QAM 14 }

		
		-- 1.3.6.1.4.1.16215.1.16.2.16.1.2.15
		ptprSSImax34M16QAM OBJECT-TYPE
			SYNTAX TypeRssiValue
			UNITS "Dbm"
			MAX-ACCESS read-write
			STATUS current
			DESCRIPTION
				"PTP rSSImax for 34M 16QAM
				DEFVAL { -68 }
				InDB = YES
				TypeInDB=INT
				ELBIT_PERM(0xFFFFFFFF)
				ADMIN_PERM(0x00000000)
				TECH_PERM(0x00000000)
				USER_PERM(0x00000000)
				"
			::= { ptp16QAM 15 }

		
		-- 1.3.6.1.4.1.16215.1.16.2.16.1.2.16
		ptppreBERmax52M16QAM OBJECT-TYPE
			SYNTAX TypePrefecBer
			MAX-ACCESS read-write
			STATUS current
			DESCRIPTION
				"PTP preBERmax for 52M 16QAM
				DEFVAL { 1E-5 }
				InDB = YES
				TypeInDB=FLOAT
				ELBIT_PERM(0xFFFFFFFF)
				ADMIN_PERM(0x00000000)
				TECH_PERM(0x00000000)
				USER_PERM(0x00000000)"
			::= { ptp16QAM 16 }

		
		-- 1.3.6.1.4.1.16215.1.16.2.16.1.2.17
		ptprSSImin52M16QAM OBJECT-TYPE
			SYNTAX TypeRssiValue
			UNITS "Dbm"
			MAX-ACCESS read-write
			STATUS current
			DESCRIPTION
				"PTP rSSImin for 52M 16QAM
				DEFVAL { -71 }
				InDB = YES
				TypeInDB=INT
				ELBIT_PERM(0xFFFFFFFF)
				ADMIN_PERM(0x00000000)
				TECH_PERM(0x00000000)
				USER_PERM(0x00000000)
				"
			::= { ptp16QAM 17 }

		
		-- 1.3.6.1.4.1.16215.1.16.2.16.1.2.18
		ptprSSImax52M16QAM OBJECT-TYPE
			SYNTAX TypeRssiValue
			UNITS "Dbm"
			MAX-ACCESS read-write
			STATUS current
			DESCRIPTION
				"PTP rSSImax for 52M 16QAM
				DEFVAL { -66 }
				InDB = YES
				TypeInDB=INT
				ELBIT_PERM(0xFFFFFFFF)
				ADMIN_PERM(0x00000000)
				TECH_PERM(0x00000000)
				USER_PERM(0x00000000)
				"
			::= { ptp16QAM 18 }

		
		-- 1.3.6.1.4.1.16215.1.16.2.16.1.2.19
		ptppreBERmax104M16QAM OBJECT-TYPE
			SYNTAX TypePrefecBer
			MAX-ACCESS read-write
			STATUS current
			DESCRIPTION
				"PTP preBERmax for 104M 16QAM
				DEFVAL { 1E-5 }
				InDB = YES
				TypeInDB=FLOAT
				ELBIT_PERM(0xFFFFFFFF)
				ADMIN_PERM(0x00000000)
				TECH_PERM(0x00000000)
				USER_PERM(0x00000000)"
			::= { ptp16QAM 19 }

		
		-- 1.3.6.1.4.1.16215.1.16.2.16.1.2.20
		ptprSSImin104M16QAM OBJECT-TYPE
			SYNTAX TypeRssiValue
			UNITS "Dbm"
			MAX-ACCESS read-write
			STATUS current
			DESCRIPTION
				"PTP rSSImin for 104M 16QAM
				DEFVAL { -67 }
				InDB = YES
				TypeInDB=INT
				ELBIT_PERM(0xFFFFFFFF)
				ADMIN_PERM(0x00000000)
				TECH_PERM(0x00000000)
				USER_PERM(0x00000000)
				"
			::= { ptp16QAM 20 }

		
		-- 1.3.6.1.4.1.16215.1.16.2.16.1.2.21
		ptprSSImax104M16QAM OBJECT-TYPE
			SYNTAX TypeRssiValue
			UNITS "Dbm"
			MAX-ACCESS read-write
			STATUS current
			DESCRIPTION
				"PTP rSSImax for 104M 16QAM
				DEFVAL { -62 }
				InDB = YES
				TypeInDB=INT
				ELBIT_PERM(0xFFFFFFFF)
				ADMIN_PERM(0x00000000)
				TECH_PERM(0x00000000)
				USER_PERM(0x00000000)
				"
			::= { ptp16QAM 21 }

		
		-- 1.3.6.1.4.1.16215.1.16.2.16.1.3
		ptpQPSK OBJECT IDENTIFIER ::= { ptp 3 }

		
		-- 1.3.6.1.4.1.16215.1.16.2.16.1.3.1
		ptppreBERmax1MQpsk OBJECT-TYPE
			SYNTAX TypePrefecBer
			MAX-ACCESS read-write
			STATUS current
			DESCRIPTION
				"PTP preBERmax for 1M Qpsk
				DEFVAL { 1E-6 }
				InDB = YES
				TypeInDB=FLOAT
				ELBIT_PERM(0xFFFFFFFF)
				ADMIN_PERM(0x00000000)
				TECH_PERM(0x00000000)
				USER_PERM(0x00000000)
				"
			::= { ptpQPSK 1 }

		
		-- 1.3.6.1.4.1.16215.1.16.2.16.1.3.2
		ptprSSImin1MQpsk OBJECT-TYPE
			SYNTAX TypeRssiValue
			UNITS "Dbm"
			MAX-ACCESS read-write
			STATUS current
			DESCRIPTION
				"PTP rSSImin for 1M Qpsk
				DEFVAL { -92 }
				InDB = YES
				TypeInDB=INT
				ELBIT_PERM(0xFFFFFFFF)
				ADMIN_PERM(0x00000000)
				TECH_PERM(0x00000000)
				USER_PERM(0x00000000)
				"
			::= { ptpQPSK 2 }

		
		-- 1.3.6.1.4.1.16215.1.16.2.16.1.3.3
		ptprSSImax1MQpsk OBJECT-TYPE
			SYNTAX TypeRssiValue
			UNITS "Dbm"
			MAX-ACCESS read-write
			STATUS current
			DESCRIPTION
				"PTP rSSImax for 1M Qpsk
				DEFVAL { -87 }
				InDB = YES
				TypeInDB=INT
				ELBIT_PERM(0xFFFFFFFF)
				ADMIN_PERM(0x00000000)
				TECH_PERM(0x00000000)
				USER_PERM(0x00000000)
				"
			::= { ptpQPSK 3 }

		
		-- 1.3.6.1.4.1.16215.1.16.2.16.1.3.4
		ptppreBERmax2MQpsk OBJECT-TYPE
			SYNTAX TypePrefecBer
			MAX-ACCESS read-write
			STATUS current
			DESCRIPTION
				"preBERmax for 2M Qpsk
				DEFVAL { 1E-6 }
				InDB = YES
				TypeInDB=FLOAT
				ELBIT_PERM(0xFFFFFFFF)
				ADMIN_PERM(0x00000000)
				TECH_PERM(0x00000000)
				USER_PERM(0x00000000)"
			::= { ptpQPSK 4 }

		
		-- 1.3.6.1.4.1.16215.1.16.2.16.1.3.5
		ptprSSImin2MQpsk OBJECT-TYPE
			SYNTAX TypeRssiValue
			UNITS "Dbm"
			MAX-ACCESS read-write
			STATUS current
			DESCRIPTION
				"PTP rSSImin for 2M Qpsk
				DEFVAL { -90 }
				InDB = YES
				TypeInDB=INT
				ELBIT_PERM(0xFFFFFFFF)
				ADMIN_PERM(0x00000000)
				TECH_PERM(0x00000000)
				USER_PERM(0x00000000)
				"
			::= { ptpQPSK 5 }

		
		-- 1.3.6.1.4.1.16215.1.16.2.16.1.3.6
		ptprSSImax2MQpsk OBJECT-TYPE
			SYNTAX TypeRssiValue
			UNITS "Dbm"
			MAX-ACCESS read-write
			STATUS current
			DESCRIPTION
				"PTP rSSImax for 2M Qpsk
				DEFVAL { -85 }
				InDB = YES
				TypeInDB=INT
				ELBIT_PERM(0xFFFFFFFF)
				ADMIN_PERM(0x00000000)
				TECH_PERM(0x00000000)
				USER_PERM(0x00000000)
				"
			::= { ptpQPSK 6 }

		
		-- 1.3.6.1.4.1.16215.1.16.2.16.1.3.7
		ptppreBERmax4MQpsk OBJECT-TYPE
			SYNTAX TypePrefecBer
			MAX-ACCESS read-write
			STATUS current
			DESCRIPTION
				"preBERmax for 4M Qpsk
				DEFVAL { 1E-6 }
				InDB = YES
				TypeInDB=FLOAT
				ELBIT_PERM(0xFFFFFFFF)
				ADMIN_PERM(0x00000000)
				TECH_PERM(0x00000000)
				USER_PERM(0x00000000)
				"
			::= { ptpQPSK 7 }

		
		-- 1.3.6.1.4.1.16215.1.16.2.16.1.3.8
		ptprSSImin4MQpsk OBJECT-TYPE
			SYNTAX TypeRssiValue
			UNITS "Dbm"
			MAX-ACCESS read-write
			STATUS current
			DESCRIPTION
				"PTP rSSImin for 4M Qpsk
				DEFVAL { -86 }
				InDB = YES
				TypeInDB=INT
				ELBIT_PERM(0xFFFFFFFF)
				ADMIN_PERM(0x00000000)
				TECH_PERM(0x00000000)
				USER_PERM(0x00000000)
				"
			::= { ptpQPSK 8 }

		
		-- 1.3.6.1.4.1.16215.1.16.2.16.1.3.9
		ptprSSImax4MQpsk OBJECT-TYPE
			SYNTAX TypeRssiValue
			UNITS "Dbm"
			MAX-ACCESS read-write
			STATUS current
			DESCRIPTION
				"PTP rSSImax for 4M Qpsk
				DEFVAL { -81 }
				InDB = YES
				TypeInDB=INT
				ELBIT_PERM(0xFFFFFFFF)
				ADMIN_PERM(0x00000000)
				TECH_PERM(0x00000000)
				USER_PERM(0x00000000)
				"
			::= { ptpQPSK 9 }

		
		-- 1.3.6.1.4.1.16215.1.16.2.16.1.3.10
		ptppreBERmax8MQpsk OBJECT-TYPE
			SYNTAX TypePrefecBer
			MAX-ACCESS read-write
			STATUS current
			DESCRIPTION
				"preBERmax for 8M Qpsk
				DEFVAL { 1E-6 }
				InDB = YES
				TypeInDB=FLOAT
				ELBIT_PERM(0xFFFFFFFF)
				ADMIN_PERM(0x00000000)
				TECH_PERM(0x00000000)
				USER_PERM(0x00000000)
				"
			::= { ptpQPSK 10 }

		
		-- 1.3.6.1.4.1.16215.1.16.2.16.1.3.11
		ptprSSImin8MQpsk OBJECT-TYPE
			SYNTAX TypeRssiValue
			UNITS "Dbm"
			MAX-ACCESS read-write
			STATUS current
			DESCRIPTION
				"PTP rSSImin for 8M Qpsk
				DEFVAL { -83 }
				InDB = YES
				TypeInDB=INT
				ELBIT_PERM(0xFFFFFFFF)
				ADMIN_PERM(0x00000000)
				TECH_PERM(0x00000000)
				USER_PERM(0x00000000)
				"
			::= { ptpQPSK 11 }

		
		-- 1.3.6.1.4.1.16215.1.16.2.16.1.3.12
		ptprSSImax8MQpsk OBJECT-TYPE
			SYNTAX TypeRssiValue
			UNITS "Dbm"
			MAX-ACCESS read-write
			STATUS current
			DESCRIPTION
				"PTP rSSImax for 8M Qpsk
				DEFVAL { -78 }
				InDB = YES
				TypeInDB=INT
				ELBIT_PERM(0xFFFFFFFF)
				ADMIN_PERM(0x00000000)
				TECH_PERM(0x00000000)
				USER_PERM(0x00000000)
				"
			::= { ptpQPSK 12 }

		
		-- 1.3.6.1.4.1.16215.1.16.2.16.1.3.13
		ptppreBERmax16MQpsk OBJECT-TYPE
			SYNTAX TypePrefecBer
			MAX-ACCESS read-write
			STATUS current
			DESCRIPTION
				"preBERmax for 16M Qpsk
				DEFVAL { 1E-6 }
				InDB = YES
				TypeInDB=FLOAT
				ELBIT_PERM(0xFFFFFFFF)
				ADMIN_PERM(0x00000000)
				TECH_PERM(0x00000000)
				USER_PERM(0x00000000)
				"
			::= { ptpQPSK 13 }

		
		-- 1.3.6.1.4.1.16215.1.16.2.16.1.3.14
		ptprSSImin16MQpsk OBJECT-TYPE
			SYNTAX TypeRssiValue
			UNITS "Dbm"
			MAX-ACCESS read-write
			STATUS current
			DESCRIPTION
				"PTP rSSImin for 16M Qpsk
				DEFVAL { -80 }
				InDB = YES
				TypeInDB=INT
				ELBIT_PERM(0xFFFFFFFF)
				ADMIN_PERM(0x00000000)
				TECH_PERM(0x00000000)
				USER_PERM(0x00000000)
				"
			::= { ptpQPSK 14 }

		
		-- 1.3.6.1.4.1.16215.1.16.2.16.1.3.15
		ptprSSImax16MQpsk OBJECT-TYPE
			SYNTAX TypeRssiValue
			UNITS "Dbm"
			MAX-ACCESS read-write
			STATUS current
			DESCRIPTION
				"PTP rSSImax for 16M Qpsk
				DEFVAL { -75 }
				InDB = YES
				TypeInDB=INT
				ELBIT_PERM(0xFFFFFFFF)
				ADMIN_PERM(0x00000000)
				TECH_PERM(0x00000000)
				USER_PERM(0x00000000)
				"
			::= { ptpQPSK 15 }

		
		-- 1.3.6.1.4.1.16215.1.16.2.16.1.3.16
		ptppreBERmax34MQpsk OBJECT-TYPE
			SYNTAX TypePrefecBer
			MAX-ACCESS read-write
			STATUS current
			DESCRIPTION
				"preBERmax for 34M Qpsk
				DEFVAL { 1E-6 }
				InDB = YES
				TypeInDB=FLOAT
				ELBIT_PERM(0xFFFFFFFF)
				ADMIN_PERM(0x00000000)
				TECH_PERM(0x00000000)
				USER_PERM(0x00000000)
				"
			::= { ptpQPSK 16 }

		
		-- 1.3.6.1.4.1.16215.1.16.2.16.1.3.17
		ptprSSImin34MQpsk OBJECT-TYPE
			SYNTAX TypeRssiValue
			UNITS "Dbm"
			MAX-ACCESS read-write
			STATUS current
			DESCRIPTION
				"PTP rSSImin for 342M Qpsk
				DEFVAL { -77 }
				InDB = YES
				TypeInDB=INT
				ELBIT_PERM(0xFFFFFFFF)
				ADMIN_PERM(0x00000000)
				TECH_PERM(0x00000000)
				USER_PERM(0x00000000)
				"
			::= { ptpQPSK 17 }

		
		-- 1.3.6.1.4.1.16215.1.16.2.16.1.3.18
		ptprSSImax34MQpsk OBJECT-TYPE
			SYNTAX TypeRssiValue
			UNITS "Dbm"
			MAX-ACCESS read-write
			STATUS current
			DESCRIPTION
				"PTP rSSImax for 34M Qpsk
				DEFVAL { -72 }
				InDB = YES
				TypeInDB=INT
				ELBIT_PERM(0xFFFFFFFF)
				ADMIN_PERM(0x00000000)
				TECH_PERM(0x00000000)
				USER_PERM(0x00000000)
				"
			::= { ptpQPSK 18 }

		
		-- 1.3.6.1.4.1.16215.1.16.2.16.2
		mpt2p OBJECT IDENTIFIER ::= { apcThreshold 2 }

		
		-- 1.3.6.1.4.1.16215.1.16.2.16.2.1
		mp64QAM OBJECT IDENTIFIER ::= { mpt2p 1 }

		
		-- 1.3.6.1.4.1.16215.1.16.2.16.2.1.1
		mppreBERmax8M64QAM OBJECT-TYPE
			SYNTAX TypePrefecBer
			MAX-ACCESS read-write
			STATUS current
			DESCRIPTION
				"MPT2P preBERmax for 8M 64QAM
				DEFVAL { 1E-6 }
				InDB = YES
				TypeInDB=FLOAT
				ELBIT_PERM(0xFFFFFFFF)
				ADMIN_PERM(0x00000000)
				TECH_PERM(0x00000000)
				USER_PERM(0x00000000)"
			::= { mp64QAM 1 }

		
		-- 1.3.6.1.4.1.16215.1.16.2.16.2.1.2
		mprSSImin8M64QAM OBJECT-TYPE
			SYNTAX TypeRssiValue
			MAX-ACCESS read-write
			STATUS current
			DESCRIPTION
				"MPT2P rSSImin for 8M 64QAM
				DEFVAL { -69 }
				InDB = YES
				TypeInDB=INT
				ELBIT_PERM(0xFFFFFFFF)
				ADMIN_PERM(0x00000000)
				TECH_PERM(0x00000000)
				USER_PERM(0x00000000)"
			::= { mp64QAM 2 }

		
		-- 1.3.6.1.4.1.16215.1.16.2.16.2.1.3
		mprSSImax8M64QAM OBJECT-TYPE
			SYNTAX TypeRssiValue
			MAX-ACCESS read-write
			STATUS current
			DESCRIPTION
				"MPT2P rSSImax for 8M 64QAM
				DEFVAL { -64 }
				InDB = YES
				TypeInDB=INT
				ELBIT_PERM(0xFFFFFFFF)
				ADMIN_PERM(0x00000000)
				TECH_PERM(0x00000000)
				USER_PERM(0x00000000)"
			::= { mp64QAM 3 }

		
		-- 1.3.6.1.4.1.16215.1.16.2.16.2.1.4
		mppreBERmax16M64QAM OBJECT-TYPE
			SYNTAX TypePrefecBer
			MAX-ACCESS read-write
			STATUS current
			DESCRIPTION
				"MPT2P preBERmax for 16M 64QAM
				DEFVAL { 1E-6 }
				InDB = YES
				TypeInDB=FLOAT
				ELBIT_PERM(0xFFFFFFFF)
				ADMIN_PERM(0x00000000)
				TECH_PERM(0x00000000)
				USER_PERM(0x00000000)"
			::= { mp64QAM 4 }

		
		-- 1.3.6.1.4.1.16215.1.16.2.16.2.1.5
		mprSSImin16M64QAM OBJECT-TYPE
			SYNTAX TypeRssiValue
			UNITS "Dbm"
			MAX-ACCESS read-write
			STATUS current
			DESCRIPTION
				"MPT2P rSSImin for 16M 64QAM
				DEFVAL { -69 }
				InDB = YES
				TypeInDB=INT
				ELBIT_PERM(0xFFFFFFFF)
				ADMIN_PERM(0x00000000)
				TECH_PERM(0x00000000)
				USER_PERM(0x00000000)"
			::= { mp64QAM 5 }

		
		-- 1.3.6.1.4.1.16215.1.16.2.16.2.1.6
		mprSSImax16M64QAM OBJECT-TYPE
			SYNTAX TypeRssiValue
			UNITS "Dbm"
			MAX-ACCESS read-write
			STATUS current
			DESCRIPTION
				"MPT2P rSSImax for 16M 64QAM
				DEFVAL { -64 }
				InDB = YES
				TypeInDB=INT
				ELBIT_PERM(0xFFFFFFFF)
				ADMIN_PERM(0x00000000)
				TECH_PERM(0x00000000)
				USER_PERM(0x00000000)"
			::= { mp64QAM 6 }

		
		-- 1.3.6.1.4.1.16215.1.16.2.16.2.1.7
		mppreBERmax34M64QAM OBJECT-TYPE
			SYNTAX TypePrefecBer
			MAX-ACCESS read-write
			STATUS current
			DESCRIPTION
				"MPT2P preBERmax for 34M 64QAM
				DEFVAL { 1E-6 }
				InDB = YES
				TypeInDB=FLOAT
				ELBIT_PERM(0xFFFFFFFF)
				ADMIN_PERM(0x00000000)
				TECH_PERM(0x00000000)
				USER_PERM(0x00000000)"
			::= { mp64QAM 7 }

		
		-- 1.3.6.1.4.1.16215.1.16.2.16.2.1.8
		mprSSImin34M64QAM OBJECT-TYPE
			SYNTAX TypeRssiValue
			UNITS "Dbm"
			MAX-ACCESS read-write
			STATUS current
			DESCRIPTION
				"MPT2P rSSImin for 34M 64QAM
				DEFVAL { -69 }
				InDB = YES
				TypeInDB=INT
				ELBIT_PERM(0xFFFFFFFF)
				ADMIN_PERM(0x00000000)
				TECH_PERM(0x00000000)
				USER_PERM(0x00000000)"
			::= { mp64QAM 8 }

		
		-- 1.3.6.1.4.1.16215.1.16.2.16.2.1.9
		mprSSImax34M64QAM OBJECT-TYPE
			SYNTAX TypeRssiValue
			UNITS "Dbm"
			MAX-ACCESS read-write
			STATUS current
			DESCRIPTION
				"MPT2P rSSImax for 34M 64QAM
				DEFVAL { -61 }
				InDB = YES
				TypeInDB=INT
				ELBIT_PERM(0xFFFFFFFF)
				ADMIN_PERM(0x00000000)
				TECH_PERM(0x00000000)
				USER_PERM(0x00000000)"
			::= { mp64QAM 9 }

		
		-- 1.3.6.1.4.1.16215.1.16.2.16.2.1.10
		mppreBERmax52M64QAM OBJECT-TYPE
			SYNTAX TypePrefecBer
			MAX-ACCESS read-write
			STATUS current
			DESCRIPTION
				"MPT2P preBERmax for 52M 64QAM
				DEFVAL { 1E-5 }
				InDB = YES
				TypeInDB=FLOAT
				ELBIT_PERM(0xFFFFFFFF)
				ADMIN_PERM(0x00000000)
				TECH_PERM(0x00000000)
				USER_PERM(0x00000000)"
			::= { mp64QAM 10 }

		
		-- 1.3.6.1.4.1.16215.1.16.2.16.2.1.11
		mprSSImin52M64QAM OBJECT-TYPE
			SYNTAX TypeRssiValue
			UNITS "Dbm"
			MAX-ACCESS read-write
			STATUS current
			DESCRIPTION
				"MPT2P rSSImin for 52M 64QAM
				DEFVAL { -64 }
				InDB = YES
				TypeInDB=INT
				ELBIT_PERM(0xFFFFFFFF)
				ADMIN_PERM(0x00000000)
				TECH_PERM(0x00000000)
				USER_PERM(0x00000000)"
			::= { mp64QAM 11 }

		
		-- 1.3.6.1.4.1.16215.1.16.2.16.2.1.12
		mprSSImax52M64QAM OBJECT-TYPE
			SYNTAX TypeRssiValue
			UNITS "Dbm"
			MAX-ACCESS read-write
			STATUS current
			DESCRIPTION
				"MPT2P rSSImax for 52M 64QAM
				DEFVAL { -59 }
				InDB = YES
				TypeInDB=INT
				ELBIT_PERM(0xFFFFFFFF)
				ADMIN_PERM(0x00000000)
				TECH_PERM(0x00000000)
				USER_PERM(0x00000000)"
			::= { mp64QAM 12 }

		
		-- 1.3.6.1.4.1.16215.1.16.2.16.2.1.13
		mppreBERmax104M64QAM OBJECT-TYPE
			SYNTAX TypePrefecBer
			MAX-ACCESS read-write
			STATUS current
			DESCRIPTION
				"MPT2P preBERmax for 104M 64QAM
				DEFVAL { 1E-5 }
				InDB = YES
				TypeInDB=FLOAT
				ELBIT_PERM(0xFFFFFFFF)
				ADMIN_PERM(0x00000000)
				TECH_PERM(0x00000000)
				USER_PERM(0x00000000)"
			::= { mp64QAM 13 }

		
		-- 1.3.6.1.4.1.16215.1.16.2.16.2.1.14
		mprSSImin104M64QAM OBJECT-TYPE
			SYNTAX TypeRssiValue
			UNITS "Dbm"
			MAX-ACCESS read-write
			STATUS current
			DESCRIPTION
				"MPT2P rSSImin for 104M 64QAM
				DEFVAL { -64 }
				InDB = YES
				TypeInDB=INT
				ELBIT_PERM(0xFFFFFFFF)
				ADMIN_PERM(0x00000000)
				TECH_PERM(0x00000000)
				USER_PERM(0x00000000)"
			::= { mp64QAM 14 }

		
		-- 1.3.6.1.4.1.16215.1.16.2.16.2.1.15
		mprSSImax104M64QAM OBJECT-TYPE
			SYNTAX TypeRssiValue
			UNITS "Dbm"
			MAX-ACCESS read-write
			STATUS current
			DESCRIPTION
				"MPT2P rSSImax for 104M 64QAM
				DEFVAL { -59 }
				InDB = YES
				TypeInDB=INT
				ELBIT_PERM(0xFFFFFFFF)
				ADMIN_PERM(0x00000000)
				TECH_PERM(0x00000000)
				USER_PERM(0x00000000)"
			::= { mp64QAM 15 }

		
		-- 1.3.6.1.4.1.16215.1.16.2.16.2.2
		mp16QAM OBJECT IDENTIFIER ::= { mpt2p 2 }

		
		-- 1.3.6.1.4.1.16215.1.16.2.16.2.2.1
		mppreBERmax2M16QAM OBJECT-TYPE
			SYNTAX TypePrefecBer
			MAX-ACCESS read-write
			STATUS current
			DESCRIPTION
				"MPT2P preBERmax for 2M 16QAM
				DEFVAL { 1E-6 }
				InDB = YES
				TypeInDB=FLOAT
				ELBIT_PERM(0xFFFFFFFF)
				ADMIN_PERM(0x00000000)
				TECH_PERM(0x00000000)
				USER_PERM(0x00000000)"
			::= { mp16QAM 1 }

		
		-- 1.3.6.1.4.1.16215.1.16.2.16.2.2.2
		mprSSImin2M16QAM OBJECT-TYPE
			SYNTAX TypeRssiValue
			UNITS "Dbm"
			MAX-ACCESS read-write
			STATUS current
			DESCRIPTION
				"MPT2P rSSImin for 2M 16QAM
				DEFVAL { -92 }
				InDB = YES
				TypeInDB=INT
				ELBIT_PERM(0xFFFFFFFF)
				ADMIN_PERM(0x00000000)
				TECH_PERM(0x00000000)
				USER_PERM(0x00000000)"
			::= { mp16QAM 2 }

		
		-- 1.3.6.1.4.1.16215.1.16.2.16.2.2.3
		mprSSImax2M16QAM OBJECT-TYPE
			SYNTAX TypeRssiValue
			UNITS "Dbm"
			MAX-ACCESS read-write
			STATUS current
			DESCRIPTION
				"MPT2P rSSImax for 2M 16QAM
				DEFVAL { -87 }
				InDB = YES
				TypeInDB=INT
				ELBIT_PERM(0xFFFFFFFF)
				ADMIN_PERM(0x00000000)
				TECH_PERM(0x00000000)
				USER_PERM(0x00000000)"
			::= { mp16QAM 3 }

		
		-- 1.3.6.1.4.1.16215.1.16.2.16.2.2.4
		mppreBERmax4M16QAM OBJECT-TYPE
			SYNTAX TypePrefecBer
			MAX-ACCESS read-write
			STATUS current
			DESCRIPTION
				"MPT2P preBERmax for 4M 16QAM
				DEFVAL { 1E-6 }
				InDB = YES
				TypeInDB=FLOAT
				ELBIT_PERM(0xFFFFFFFF)
				ADMIN_PERM(0x00000000)
				TECH_PERM(0x00000000)
				USER_PERM(0x00000000)"
			::= { mp16QAM 4 }

		
		-- 1.3.6.1.4.1.16215.1.16.2.16.2.2.5
		mprSSImin4M16QAM OBJECT-TYPE
			SYNTAX TypeRssiValue
			UNITS "Dbm"
			MAX-ACCESS read-write
			STATUS current
			DESCRIPTION
				"MPT2P rSSImin for 4M 16QAM
				DEFVAL { -82 }
				InDB = YES
				TypeInDB=INT
				ELBIT_PERM(0xFFFFFFFF)
				ADMIN_PERM(0x00000000)
				TECH_PERM(0x00000000)
				USER_PERM(0x00000000)"
			::= { mp16QAM 5 }

		
		-- 1.3.6.1.4.1.16215.1.16.2.16.2.2.6
		mprSSImax4M16QAM OBJECT-TYPE
			SYNTAX TypeRssiValue
			UNITS "Dbm"
			MAX-ACCESS read-write
			STATUS current
			DESCRIPTION
				"MPT2P rSSImax for 4M 16QAM
				DEFVAL { -77 }
				InDB = YES
				TypeInDB=INT
				ELBIT_PERM(0xFFFFFFFF)
				ADMIN_PERM(0x00000000)
				TECH_PERM(0x00000000)
				USER_PERM(0x00000000)"
			::= { mp16QAM 6 }

		
		-- 1.3.6.1.4.1.16215.1.16.2.16.2.2.7
		mppreBERmax8M16QAM OBJECT-TYPE
			SYNTAX TypePrefecBer
			MAX-ACCESS read-write
			STATUS current
			DESCRIPTION
				"MPT2P preBERmax for 8M 16QAM
				DEFVAL { 1E-6 }
				InDB = YES
				TypeInDB=FLOAT
				ELBIT_PERM(0xFFFFFFFF)
				ADMIN_PERM(0x00000000)
				TECH_PERM(0x00000000)
				USER_PERM(0x00000000)"
			::= { mp16QAM 7 }

		
		-- 1.3.6.1.4.1.16215.1.16.2.16.2.2.8
		mprSSImin8M16QAM OBJECT-TYPE
			SYNTAX TypeRssiValue
			UNITS "Dbm"
			MAX-ACCESS read-write
			STATUS current
			DESCRIPTION
				"MPT2P rSSImin for 8M 16QAM
				DEFVAL { -79 }
				InDB = YES
				TypeInDB=INT
				ELBIT_PERM(0xFFFFFFFF)
				ADMIN_PERM(0x00000000)
				TECH_PERM(0x00000000)
				USER_PERM(0x00000000)"
			::= { mp16QAM 8 }

		
		-- 1.3.6.1.4.1.16215.1.16.2.16.2.2.9
		mprSSImax8M16QAM OBJECT-TYPE
			SYNTAX TypeRssiValue
			UNITS "Dbm"
			MAX-ACCESS read-write
			STATUS current
			DESCRIPTION
				"MPT2P rSSImax for 8M 16QAM
				DEFVAL { -74 }
				InDB = YES
				TypeInDB=INT
				ELBIT_PERM(0xFFFFFFFF)
				ADMIN_PERM(0x00000000)
				TECH_PERM(0x00000000)
				USER_PERM(0x00000000)"
			::= { mp16QAM 9 }

		
		-- 1.3.6.1.4.1.16215.1.16.2.16.2.2.10
		mppreBERmax16M16QAM OBJECT-TYPE
			SYNTAX TypePrefecBer
			MAX-ACCESS read-write
			STATUS current
			DESCRIPTION
				"MPT2P preBERmax for 16M 16QAM
				DEFVAL { 1E-6 }
				InDB = YES
				TypeInDB=FLOAT
				ELBIT_PERM(0xFFFFFFFF)
				ADMIN_PERM(0x00000000)
				TECH_PERM(0x00000000)
				USER_PERM(0x00000000)"
			::= { mp16QAM 10 }

		
		-- 1.3.6.1.4.1.16215.1.16.2.16.2.2.11
		mprSSImin16M16QAM OBJECT-TYPE
			SYNTAX TypeRssiValue
			UNITS "Dbm"
			MAX-ACCESS read-write
			STATUS current
			DESCRIPTION
				"MPT2P rSSImin for 16M 16QAM
				DEFVAL { -75 }
				InDB = YES
				TypeInDB=INT
				ELBIT_PERM(0xFFFFFFFF)
				ADMIN_PERM(0x00000000)
				TECH_PERM(0x00000000)
				USER_PERM(0x00000000)"
			::= { mp16QAM 11 }

		
		-- 1.3.6.1.4.1.16215.1.16.2.16.2.2.12
		mprSSImax16M16QAM OBJECT-TYPE
			SYNTAX TypeRssiValue
			UNITS "Dbm"
			MAX-ACCESS read-write
			STATUS current
			DESCRIPTION
				"MPT2P rSSImax for 16M 16QAM
				DEFVAL { -71 }
				InDB = YES
				TypeInDB=INT
				ELBIT_PERM(0xFFFFFFFF)
				ADMIN_PERM(0x00000000)
				TECH_PERM(0x00000000)
				USER_PERM(0x00000000)"
			::= { mp16QAM 12 }

		
		-- 1.3.6.1.4.1.16215.1.16.2.16.2.2.13
		mppreBERmax34M16QAM OBJECT-TYPE
			SYNTAX TypePrefecBer
			MAX-ACCESS read-write
			STATUS current
			DESCRIPTION
				"MPT2P preBERmax for 34M 16QAM
				DEFVAL { 1E-6 }
				InDB = YES
				TypeInDB=FLOAT
				ELBIT_PERM(0xFFFFFFFF)
				ADMIN_PERM(0x00000000)
				TECH_PERM(0x00000000)
				USER_PERM(0x00000000)"
			::= { mp16QAM 13 }

		
		-- 1.3.6.1.4.1.16215.1.16.2.16.2.2.14
		mprSSImin34M16QAM OBJECT-TYPE
			SYNTAX TypeRssiValue
			UNITS "Dbm"
			MAX-ACCESS read-write
			STATUS current
			DESCRIPTION
				"MPT2P rSSImin for 34M 16QAM
				DEFVAL { -73 }
				InDB = YES
				TypeInDB=INT
				ELBIT_PERM(0xFFFFFFFF)
				ADMIN_PERM(0x00000000)
				TECH_PERM(0x00000000)
				USER_PERM(0x00000000)"
			::= { mp16QAM 14 }

		
		-- 1.3.6.1.4.1.16215.1.16.2.16.2.2.15
		mprSSImax34M16QAM OBJECT-TYPE
			SYNTAX TypeRssiValue
			UNITS "Dbm"
			MAX-ACCESS read-write
			STATUS current
			DESCRIPTION
				"MPT2P rSSImax for 34M 16QAM
				DEFVAL { -68 }
				InDB = YES
				TypeInDB=INT
				ELBIT_PERM(0xFFFFFFFF)
				ADMIN_PERM(0x00000000)
				TECH_PERM(0x00000000)
				USER_PERM(0x00000000)"
			::= { mp16QAM 15 }

		
		-- 1.3.6.1.4.1.16215.1.16.2.16.2.2.16
		mppreBERmax52M16QAM OBJECT-TYPE
			SYNTAX TypePrefecBer
			MAX-ACCESS read-write
			STATUS current
			DESCRIPTION
				"MPT2P preBERmax for 52M 16QAM
				DEFVAL { 1E-5 }
				InDB = YES
				TypeInDB=FLOAT
				ELBIT_PERM(0xFFFFFFFF)
				ADMIN_PERM(0x00000000)
				TECH_PERM(0x00000000)
				USER_PERM(0x00000000)"
			::= { mp16QAM 16 }

		
		-- 1.3.6.1.4.1.16215.1.16.2.16.2.2.17
		mprSSImin52M16QAM OBJECT-TYPE
			SYNTAX TypeRssiValue
			UNITS "Dbm"
			MAX-ACCESS read-write
			STATUS current
			DESCRIPTION
				"MPT2P rSSImin for 52M 16QAM
				DEFVAL { -71 }
				InDB = YES
				TypeInDB=INT
				ELBIT_PERM(0xFFFFFFFF)
				ADMIN_PERM(0x00000000)
				TECH_PERM(0x00000000)
				USER_PERM(0x00000000)"
			::= { mp16QAM 17 }

		
		-- 1.3.6.1.4.1.16215.1.16.2.16.2.2.18
		mprSSImax52M16QAM OBJECT-TYPE
			SYNTAX TypeRssiValue
			UNITS "Dbm"
			MAX-ACCESS read-write
			STATUS current
			DESCRIPTION
				"MPT2P rSSImax for 52M 16QAM
				DEFVAL { -66 }
				InDB = YES
				TypeInDB=INT
				ELBIT_PERM(0xFFFFFFFF)
				ADMIN_PERM(0x00000000)
				TECH_PERM(0x00000000)
				USER_PERM(0x00000000)"
			::= { mp16QAM 18 }

		
		-- 1.3.6.1.4.1.16215.1.16.2.16.2.2.19
		mppreBERmax104M16QAM OBJECT-TYPE
			SYNTAX TypePrefecBer
			MAX-ACCESS read-write
			STATUS current
			DESCRIPTION
				"MPT2P preBERmax for 104M 16QAM
				DEFVAL { 1E-5 }
				InDB = YES
				TypeInDB=FLOAT
				ELBIT_PERM(0xFFFFFFFF)
				ADMIN_PERM(0x00000000)
				TECH_PERM(0x00000000)
				USER_PERM(0x00000000)"
			::= { mp16QAM 19 }

		
		-- 1.3.6.1.4.1.16215.1.16.2.16.2.2.20
		mprSSImin104M16QAM OBJECT-TYPE
			SYNTAX TypeRssiValue
			UNITS "Dbm"
			MAX-ACCESS read-write
			STATUS current
			DESCRIPTION
				"MPT2P rSSImin for 104M 16QAM
				DEFVAL { -71 }
				InDB = YES
				TypeInDB=INT
				ELBIT_PERM(0xFFFFFFFF)
				ADMIN_PERM(0x00000000)
				TECH_PERM(0x00000000)
				USER_PERM(0x00000000)"
			::= { mp16QAM 20 }

		
		-- 1.3.6.1.4.1.16215.1.16.2.16.2.2.21
		mprSSImax104M16QAM OBJECT-TYPE
			SYNTAX TypeRssiValue
			UNITS "Dbm"
			MAX-ACCESS read-write
			STATUS current
			DESCRIPTION
				"MPT2P rSSImax for 104M 16QAM
				DEFVAL { -66 }
				InDB = YES
				TypeInDB=INT
				ELBIT_PERM(0xFFFFFFFF)
				ADMIN_PERM(0x00000000)
				TECH_PERM(0x00000000)
				USER_PERM(0x00000000)"
			::= { mp16QAM 21 }

		
		-- 1.3.6.1.4.1.16215.1.16.2.16.2.3
		mpQPSK OBJECT IDENTIFIER ::= { mpt2p 3 }

		
		-- 1.3.6.1.4.1.16215.1.16.2.16.2.3.1
		mpreBERmax1MQpsk OBJECT-TYPE
			SYNTAX TypePrefecBer
			MAX-ACCESS read-write
			STATUS current
			DESCRIPTION
				"preBERmax for 1M Qpsk
				DEFVAL { 1E-6 }
				InDB = YES
				TypeInDB=FLOAT
				ELBIT_PERM(0xFFFFFFFF)
				ADMIN_PERM(0x00000000)
				TECH_PERM(0x00000000)
				USER_PERM(0x00000000)"
			::= { mpQPSK 1 }

		
		-- 1.3.6.1.4.1.16215.1.16.2.16.2.3.2
		mprSSImin1MQpsk OBJECT-TYPE
			SYNTAX TypeRssiValue
			UNITS "Dbm"
			MAX-ACCESS read-write
			STATUS current
			DESCRIPTION
				"MPT2P rSSImin for 1M Qpsk
				DEFVAL { -92 }
				InDB = YES
				TypeInDB=INT
				ELBIT_PERM(0xFFFFFFFF)
				ADMIN_PERM(0x00000000)
				TECH_PERM(0x00000000)
				USER_PERM(0x00000000)
				"
			::= { mpQPSK 2 }

		
		-- 1.3.6.1.4.1.16215.1.16.2.16.2.3.3
		mprSSImax1MQpsk OBJECT-TYPE
			SYNTAX TypeRssiValue
			UNITS "Dbm"
			MAX-ACCESS read-write
			STATUS current
			DESCRIPTION
				"MPT2P rSSImax for 1M Qpsk
				DEFVAL { -87 }
				InDB = YES
				TypeInDB=INT
				ELBIT_PERM(0xFFFFFFFF)
				ADMIN_PERM(0x00000000)
				TECH_PERM(0x00000000)
				USER_PERM(0x00000000)
				"
			::= { mpQPSK 3 }

		
		-- 1.3.6.1.4.1.16215.1.16.2.16.2.3.4
		mpreBERmax2MQpsk OBJECT-TYPE
			SYNTAX TypePrefecBer
			MAX-ACCESS read-write
			STATUS current
			DESCRIPTION
				"preBERmax for 2M Qpsk
				DEFVAL { 1E-6 }
				InDB = YES
				TypeInDB=FLOAT
				ELBIT_PERM(0xFFFFFFFF)
				ADMIN_PERM(0x00000000)
				TECH_PERM(0x00000000)
				USER_PERM(0x00000000)"
			::= { mpQPSK 4 }

		
		-- 1.3.6.1.4.1.16215.1.16.2.16.2.3.5
		mprSSImin2MQpsk OBJECT-TYPE
			SYNTAX TypeRssiValue
			UNITS "Dbm"
			MAX-ACCESS read-write
			STATUS current
			DESCRIPTION
				"MPT2P rSSImin for 2M Qpsk
				DEFVAL { -90 }
				InDB = YES
				TypeInDB=INT
				ELBIT_PERM(0xFFFFFFFF)
				ADMIN_PERM(0x00000000)
				TECH_PERM(0x00000000)
				USER_PERM(0x00000000)
				"
			::= { mpQPSK 5 }

		
		-- 1.3.6.1.4.1.16215.1.16.2.16.2.3.6
		mprSSImax2MQpsk OBJECT-TYPE
			SYNTAX TypeRssiValue
			UNITS "Dbm"
			MAX-ACCESS read-write
			STATUS current
			DESCRIPTION
				"MPT2P rSSImax for 2M Qpsk
				DEFVAL { -85 }
				InDB = YES
				TypeInDB=INT
				ELBIT_PERM(0xFFFFFFFF)
				ADMIN_PERM(0x00000000)
				TECH_PERM(0x00000000)
				USER_PERM(0x00000000)
				"
			::= { mpQPSK 6 }

		
		-- 1.3.6.1.4.1.16215.1.16.2.16.2.3.7
		mpreBERmax4MQpsk OBJECT-TYPE
			SYNTAX TypePrefecBer
			MAX-ACCESS read-write
			STATUS current
			DESCRIPTION
				"preBERmax for 4M Qpsk
				DEFVAL { 1E-6 }
				InDB = YES
				TypeInDB=FLOAT
				ELBIT_PERM(0xFFFFFFFF)
				ADMIN_PERM(0x00000000)
				TECH_PERM(0x00000000)
				USER_PERM(0x00000000)"
			::= { mpQPSK 7 }

		
		-- 1.3.6.1.4.1.16215.1.16.2.16.2.3.8
		mprSSImin4MQpsk OBJECT-TYPE
			SYNTAX TypeRssiValue
			UNITS "Dbm"
			MAX-ACCESS read-write
			STATUS current
			DESCRIPTION
				"MPT2P rSSImin for 4M Qpsk
				DEFVAL { -86 }
				InDB = YES
				TypeInDB=INT
				ELBIT_PERM(0xFFFFFFFF)
				ADMIN_PERM(0x00000000)
				TECH_PERM(0x00000000)
				USER_PERM(0x00000000)
				"
			::= { mpQPSK 8 }

		
		-- 1.3.6.1.4.1.16215.1.16.2.16.2.3.9
		mprSSImax4MQpsk OBJECT-TYPE
			SYNTAX TypeRssiValue
			UNITS "Dbm"
			MAX-ACCESS read-write
			STATUS current
			DESCRIPTION
				"MPT2P rSSImax for 4M Qpsk
				DEFVAL { -81 }
				InDB = YES
				TypeInDB=INT
				ELBIT_PERM(0xFFFFFFFF)
				ADMIN_PERM(0x00000000)
				TECH_PERM(0x00000000)
				USER_PERM(0x00000000)
				"
			::= { mpQPSK 9 }

		
		-- 1.3.6.1.4.1.16215.1.16.2.16.2.3.10
		mpreBERmax8MQpsk OBJECT-TYPE
			SYNTAX TypePrefecBer
			MAX-ACCESS read-write
			STATUS current
			DESCRIPTION
				"preBERmax for 8M Qpsk
				DEFVAL { 1E-6 }
				InDB = YES
				TypeInDB=FLOAT
				ELBIT_PERM(0xFFFFFFFF)
				ADMIN_PERM(0x00000000)
				TECH_PERM(0x00000000)
				USER_PERM(0x00000000)"
			::= { mpQPSK 10 }

		
		-- 1.3.6.1.4.1.16215.1.16.2.16.2.3.11
		mprSSImin8MQpsk OBJECT-TYPE
			SYNTAX TypeRssiValue
			UNITS "Dbm"
			MAX-ACCESS read-write
			STATUS current
			DESCRIPTION
				"MPT2P rSSImin for 8M Qpsk
				DEFVAL { -83 }
				InDB = YES
				TypeInDB=INT
				ELBIT_PERM(0xFFFFFFFF)
				ADMIN_PERM(0x00000000)
				TECH_PERM(0x00000000)
				USER_PERM(0x00000000)
				"
			::= { mpQPSK 11 }

		
		-- 1.3.6.1.4.1.16215.1.16.2.16.2.3.12
		mprSSImax8MQpsk OBJECT-TYPE
			SYNTAX TypeRssiValue
			UNITS "Dbm"
			MAX-ACCESS read-write
			STATUS current
			DESCRIPTION
				"MPT2P rSSImax for 8M Qpsk
				DEFVAL { -78 }
				InDB = YES
				TypeInDB=INT
				ELBIT_PERM(0xFFFFFFFF)
				ADMIN_PERM(0x00000000)
				TECH_PERM(0x00000000)
				USER_PERM(0x00000000)
				"
			::= { mpQPSK 12 }

		
		-- 1.3.6.1.4.1.16215.1.16.2.16.2.3.13
		mpreBERmax16MQpsk OBJECT-TYPE
			SYNTAX TypePrefecBer
			MAX-ACCESS read-write
			STATUS current
			DESCRIPTION
				"preBERmax for 16M Qpsk
				DEFVAL { 1E-6 }
				InDB = YES
				TypeInDB=FLOAT
				ELBIT_PERM(0xFFFFFFFF)
				ADMIN_PERM(0x00000000)
				TECH_PERM(0x00000000)
				USER_PERM(0x00000000)"
			::= { mpQPSK 13 }

		
		-- 1.3.6.1.4.1.16215.1.16.2.16.2.3.14
		mprSSImin16MQpsk OBJECT-TYPE
			SYNTAX TypeRssiValue
			UNITS "Dbm"
			MAX-ACCESS read-write
			STATUS current
			DESCRIPTION
				"MPT2P rSSImin for 16M Qpsk
				DEFVAL { -80 }
				InDB = YES
				TypeInDB=INT
				ELBIT_PERM(0xFFFFFFFF)
				ADMIN_PERM(0x00000000)
				TECH_PERM(0x00000000)
				USER_PERM(0x00000000)
				"
			::= { mpQPSK 14 }

		
		-- 1.3.6.1.4.1.16215.1.16.2.16.2.3.15
		mprSSImax16MQpsk OBJECT-TYPE
			SYNTAX TypeRssiValue
			UNITS "Dbm"
			MAX-ACCESS read-write
			STATUS current
			DESCRIPTION
				"MPT2P rSSImaz for 16M Qpsk
				DEFVAL { -75 }
				InDB = YES
				TypeInDB=INT
				ELBIT_PERM(0xFFFFFFFF)
				ADMIN_PERM(0x00000000)
				TECH_PERM(0x00000000)
				USER_PERM(0x00000000)
				"
			::= { mpQPSK 15 }

		
		-- 1.3.6.1.4.1.16215.1.16.2.16.2.3.16
		mpreBERmax34MQpsk OBJECT-TYPE
			SYNTAX TypePrefecBer
			MAX-ACCESS read-write
			STATUS current
			DESCRIPTION
				"preBERmax for 34M Qpsk
				DEFVAL { 1E-6 }
				InDB = YES
				TypeInDB=FLOAT
				ELBIT_PERM(0xFFFFFFFF)
				ADMIN_PERM(0x00000000)
				TECH_PERM(0x00000000)
				USER_PERM(0x00000000)"
			::= { mpQPSK 16 }

		
		-- 1.3.6.1.4.1.16215.1.16.2.16.2.3.17
		mprSSImin34MQpsk OBJECT-TYPE
			SYNTAX TypeRssiValue
			UNITS "Dbm"
			MAX-ACCESS read-write
			STATUS current
			DESCRIPTION
				"MPT2P rSSImin for 34M Qpsk
				DEFVAL { -77 }
				InDB = YES
				TypeInDB=INT
				ELBIT_PERM(0xFFFFFFFF)
				ADMIN_PERM(0x00000000)
				TECH_PERM(0x00000000)
				USER_PERM(0x00000000)"
			::= { mpQPSK 17 }

		
		-- 1.3.6.1.4.1.16215.1.16.2.16.2.3.18
		mprSSImax34MQpsk OBJECT-TYPE
			SYNTAX TypeRssiValue
			UNITS "Dbm"
			MAX-ACCESS read-write
			STATUS current
			DESCRIPTION
				"MPT2P rSSImax for 34M Qpsk
				DEFVAL { -72 }
				InDB = YES
				TypeInDB=INT
				ELBIT_PERM(0xFFFFFFFF)
				ADMIN_PERM(0x00000000)
				TECH_PERM(0x00000000)
				USER_PERM(0x00000000)"
			::= { mpQPSK 18 }

		
--  1.3.6.1.4.1.16215.1.16.1.15
		-- 1.3.6.1.4.1.16215.1.16.2.17
		hwOperation OBJECT IDENTIFIER ::= { odu 17 }

		
		-- 1.3.6.1.4.1.16215.1.16.2.17.1
		hwRegReadWrite OBJECT IDENTIFIER ::= { hwOperation 1 }

		
		-- 1.3.6.1.4.1.16215.1.16.2.17.1.1
		hwReadWriteAddress OBJECT-TYPE
			SYNTAX Integer32 (0..65535)
			MAX-ACCESS read-write
			STATUS current
			DESCRIPTION
				"Description."
			::= { hwRegReadWrite 1 }

		
		-- 1.3.6.1.4.1.16215.1.16.2.17.1.2
		hwRWregValue OBJECT-TYPE
			SYNTAX INTEGER (0..255)
			MAX-ACCESS read-write
			STATUS current
			DESCRIPTION
				"HW Fpga egister Value
				InDB = NO
				ELBIT_PERM(0xFFFFFFFF)
				ADMIN_PERM(0x00000000)
				TECH_PERM(0x00000000)
				USER_PERM(0x00000000)"
			::= { hwRegReadWrite 2 }

		
		-- 1.3.6.1.4.1.16215.1.16.2.17.2
		hwRegReadOnly OBJECT IDENTIFIER ::= { hwOperation 2 }

		
		-- 1.3.6.1.4.1.16215.1.16.2.17.2.1
		hwReadOnlyRegAddress OBJECT-TYPE
			SYNTAX TypeFpgaRegAddress
			MAX-ACCESS read-write
			STATUS current
			DESCRIPTION
				"FPGA register addres where reading from
				InDB = NO
				ELBIT_PERM(0xFFFFFFFF)
				ADMIN_PERM(0x00000000)
				TECH_PERM(0x00000000)
				USER_PERM(0x00000000)"
			::= { hwRegReadOnly 1 }

		
		-- 1.3.6.1.4.1.16215.1.16.2.17.2.2
		hwReadOnlyRegValue OBJECT-TYPE
			SYNTAX Integer32 (0..255)
			MAX-ACCESS read-only
			STATUS current
			DESCRIPTION
				"Value of FPGA register
				InDB = NO
				ELBIT_PERM(0xFFFFFFFF)
				ADMIN_PERM(0x00000000)
				TECH_PERM(0x00000000)
				USER_PERM(0x00000000)"
			::= { hwRegReadOnly 2 }

		
		-- 1.3.6.1.4.1.16215.1.16.2.18
		antennaParameters OBJECT IDENTIFIER ::= { odu 18 }

		
		-- 1.3.6.1.4.1.16215.1.16.2.18.1
		compassParameters OBJECT IDENTIFIER ::= { antennaParameters 1 }

		
		-- 1.3.6.1.4.1.16215.1.16.2.18.1.1
		getCompassParameters OBJECT-TYPE
			SYNTAX TypeOnOff
			MAX-ACCESS read-write
			STATUS current
			DESCRIPTION
				"Send Command TO Compass to read Parameters
				InDB = NO
				ELBIT_PERM(0xFFFFFFFF)
				ADMIN_PERM(0xFFFFFFFF)
				TECH_PERM(0xFFFFFFFF)
				USER_PERM(0xFFFFFFFF)"
			::= { compassParameters 1 }

		
		-- 1.3.6.1.4.1.16215.1.16.2.18.1.2
		readCompassParameters OBJECT-TYPE
			SYNTAX TypeOnOff
			MAX-ACCESS read-write
			STATUS current
			DESCRIPTION
				"Read Antenna Rotator CompassInDB = NO
				ELBIT_PERM(0xFFFFFFFF)
				ADMIN_PERM(0xFFFFFFFF)
				TECH_PERM(0xFFFFFFFF)
				USER_PERM(0xFFFFFFFF)"
			::= { compassParameters 2 }

		
		-- 1.3.6.1.4.1.16215.1.16.2.18.1.3
		compassEndian OBJECT-TYPE
			SYNTAX TypeEndian
			MAX-ACCESS read-only
			STATUS current
			DESCRIPTION
				"Compass Endian working Mode
				1 - Big Endian
				2 - Little Endian
				InDB = NO
				ELBIT_PERM(0xFFFFFFFF)
				ADMIN_PERM(0xFFFFFFFF)
				TECH_PERM(0xFFFFFFFF)
				USER_PERM(0xFFFFFFFF)"
			::= { compassParameters 3 }

		
		-- 1.3.6.1.4.1.16215.1.16.2.18.1.4
		accelParametersFactor OBJECT-TYPE
			SYNTAX TypeFactorMulOrDiv
			MAX-ACCESS read-only
			STATUS current
			DESCRIPTION
				"Acceleration Use factor multiply or Divide
				InDB = NO
				ELBIT_PERM(0xFFFFFFFF)
				ADMIN_PERM(0xFFFFFFFF)
				TECH_PERM(0xFFFFFFFF)
				USER_PERM(0xFFFFFFFF)"
			::= { compassParameters 4 }

		
		-- 1.3.6.1.4.1.16215.1.16.2.18.1.5
		acceleratorFactor OBJECT-TYPE
			SYNTAX Integer32
			MAX-ACCESS read-only
			STATUS current
			DESCRIPTION
				"Accelarator Factor
				InDB = NO
				ELBIT_PERM(0xFFFFFFFF)
				ADMIN_PERM(0xFFFFFFFF)
				TECH_PERM(0xFFFFFFFF)
				USER_PERM(0xFFFFFFFF)"
			::= { compassParameters 5 }

		
		-- 1.3.6.1.4.1.16215.1.16.2.18.1.6
		postAccelDataAx OBJECT-TYPE
			SYNTAX Integer32
			MAX-ACCESS read-only
			STATUS current
			DESCRIPTION
				"Post Accelerator Data Ax
				InDB = NO
				ELBIT_PERM(0xFFFFFFFF)
				ADMIN_PERM(0xFFFFFFFF)
				TECH_PERM(0xFFFFFFFF)
				USER_PERM(0xFFFFFFFF)
				"
			::= { compassParameters 6 }

		
		-- 1.3.6.1.4.1.16215.1.16.2.18.1.7
		postAccelDataAy OBJECT-TYPE
			SYNTAX Integer32
			MAX-ACCESS read-only
			STATUS current
			DESCRIPTION
				"Post Accelerator Data Ay
				InDB = NO
				ELBIT_PERM(0xFFFFFFFF)
				ADMIN_PERM(0xFFFFFFFF)
				TECH_PERM(0xFFFFFFFF)
				USER_PERM(0xFFFFFFFF)"
			::= { compassParameters 7 }

		
		-- 1.3.6.1.4.1.16215.1.16.2.18.1.8
		postAccelDataAz OBJECT-TYPE
			SYNTAX Integer32
			MAX-ACCESS read-only
			STATUS current
			DESCRIPTION
				"Post Accelerator Data Az
				InDB = NO
				ELBIT_PERM(0xFFFFFFFF)
				ADMIN_PERM(0xFFFFFFFF)
				TECH_PERM(0xFFFFFFFF)
				USER_PERM(0xFFFFFFFF)"
			::= { compassParameters 8 }

		
		-- 1.3.6.1.4.1.16215.1.16.2.18.1.9
		magParametersFactor OBJECT-TYPE
			SYNTAX TypeFactorMulOrDiv
			MAX-ACCESS read-only
			STATUS current
			DESCRIPTION
				"Magnitude Use factor multiply or Divide
				InDB = NO
				ELBIT_PERM(0xFFFFFFFF)
				ADMIN_PERM(0xFFFFFFFF)
				TECH_PERM(0xFFFFFFFF)
				USER_PERM(0xFFFFFFFF)"
			::= { compassParameters 9 }

		
		-- 1.3.6.1.4.1.16215.1.16.2.18.1.10
		magnitudeFactor OBJECT-TYPE
			SYNTAX Integer32
			MAX-ACCESS read-only
			STATUS current
			DESCRIPTION
				"Magnitude Use factor 
				InDB = NO
				ELBIT_PERM(0xFFFFFFFF)
				ADMIN_PERM(0xFFFFFFFF)
				TECH_PERM(0xFFFFFFFF)
				USER_PERM(0xFFFFFFFF)"
			::= { compassParameters 10 }

		
		-- 1.3.6.1.4.1.16215.1.16.2.18.1.11
		postmagDataAx OBJECT-TYPE
			SYNTAX Integer32
			MAX-ACCESS read-only
			STATUS current
			DESCRIPTION
				"Post Magnitude Data Ax
				InDB = NO
				ELBIT_PERM(0xFFFFFFFF)
				ADMIN_PERM(0xFFFFFFFF)
				TECH_PERM(0xFFFFFFFF)
				USER_PERM(0xFFFFFFFF)
				"
			::= { compassParameters 11 }

		
		-- 1.3.6.1.4.1.16215.1.16.2.18.1.12
		postmagDataAy OBJECT-TYPE
			SYNTAX Integer32
			MAX-ACCESS read-only
			STATUS current
			DESCRIPTION
				"Post Magnitude Data Ay
				InDB = NO
				ELBIT_PERM(0xFFFFFFFF)
				ADMIN_PERM(0xFFFFFFFF)
				TECH_PERM(0xFFFFFFFF)
				USER_PERM(0xFFFFFFFF)
				"
			::= { compassParameters 12 }

		
		-- 1.3.6.1.4.1.16215.1.16.2.18.1.13
		postmagDataAz OBJECT-TYPE
			SYNTAX Integer32
			MAX-ACCESS read-only
			STATUS current
			DESCRIPTION
				"Post Magnitude Data Ay
				InDB = NO
				ELBIT_PERM(0xFFFFFFFF)
				ADMIN_PERM(0xFFFFFFFF)
				TECH_PERM(0xFFFFFFFF)
				USER_PERM(0xFFFFFFFF)
				"
			::= { compassParameters 13 }

		
		-- 1.3.6.1.4.1.16215.1.16.2.18.1.14
		headingParametersFactor OBJECT-TYPE
			SYNTAX TypeFactorMulOrDiv
			MAX-ACCESS read-only
			STATUS current
			DESCRIPTION
				"Heading Use factor multiply or Divide
				InDB = NO
				ELBIT_PERM(0xFFFFFFFF)
				ADMIN_PERM(0xFFFFFFFF)
				TECH_PERM(0xFFFFFFFF)
				USER_PERM(0xFFFFFFFF)"
			::= { compassParameters 14 }

		
		-- 1.3.6.1.4.1.16215.1.16.2.18.1.15
		headingeFactor OBJECT-TYPE
			SYNTAX Integer32
			MAX-ACCESS read-only
			STATUS current
			DESCRIPTION
				"Heading Use factor 
				InDB = NO
				ELBIT_PERM(0xFFFFFFFF)
				ADMIN_PERM(0xFFFFFFFF)
				TECH_PERM(0xFFFFFFFF)
				USER_PERM(0xFFFFFFFF)"
			::= { compassParameters 15 }

		
		-- 1.3.6.1.4.1.16215.1.16.2.18.1.16
		postHeadingDataHead OBJECT-TYPE
			SYNTAX Integer32
			MAX-ACCESS read-only
			STATUS current
			DESCRIPTION
				"Post Heading Data Head
				InDB = NO
				ELBIT_PERM(0xFFFFFFFF)
				ADMIN_PERM(0xFFFFFFFF)
				TECH_PERM(0xFFFFFFFF)
				USER_PERM(0xFFFFFFFF)
				"
			::= { compassParameters 16 }

		
		-- 1.3.6.1.4.1.16215.1.16.2.18.1.17
		postHeadingDataPitch OBJECT-TYPE
			SYNTAX Integer32
			MAX-ACCESS read-only
			STATUS current
			DESCRIPTION
				"Post Heading Data Pitch
				InDB = NO
				ELBIT_PERM(0xFFFFFFFF)
				ADMIN_PERM(0xFFFFFFFF)
				TECH_PERM(0xFFFFFFFF)
				USER_PERM(0xFFFFFFFF)
				"
			::= { compassParameters 17 }

		
		-- 1.3.6.1.4.1.16215.1.16.2.18.1.18
		postHeadingDataRoll OBJECT-TYPE
			SYNTAX Integer32
			MAX-ACCESS read-only
			STATUS current
			DESCRIPTION
				"Tilt Use factor multiply or Divide
				InDB = NO
				ELBIT_PERM(0xFFFFFFFF)
				ADMIN_PERM(0xFFFFFFFF)
				TECH_PERM(0xFFFFFFFF)
				USER_PERM(0xFFFFFFFF)
				"
			::= { compassParameters 18 }

		
		-- 1.3.6.1.4.1.16215.1.16.2.18.1.19
		tiltParametersFactor OBJECT-TYPE
			SYNTAX Integer32
			MAX-ACCESS read-only
			STATUS current
			DESCRIPTION
				"Tilt Use factor multiply or Divide
				InDB = NO
				ELBIT_PERM(0xFFFFFFFF)
				ADMIN_PERM(0xFFFFFFFF)
				TECH_PERM(0xFFFFFFFF)
				USER_PERM(0xFFFFFFFF)"
			::= { compassParameters 19 }

		
		-- 1.3.6.1.4.1.16215.1.16.2.18.1.20
		tiltFactor OBJECT-TYPE
			SYNTAX Integer32
			MAX-ACCESS read-only
			STATUS current
			DESCRIPTION
				"Tilt Use factor 
				InDB = NO
				ELBIT_PERM(0xFFFFFFFF)
				ADMIN_PERM(0xFFFFFFFF)
				TECH_PERM(0xFFFFFFFF)
				USER_PERM(0xFFFFFFFF)"
			::= { compassParameters 20 }

		
		-- 1.3.6.1.4.1.16215.1.16.2.18.1.21
		postTiltDataPitch OBJECT-TYPE
			SYNTAX Integer32
			MAX-ACCESS read-only
			STATUS current
			DESCRIPTION
				"Post Tilt Data Pitch
				InDB = NO
				ELBIT_PERM(0xFFFFFFFF)
				ADMIN_PERM(0xFFFFFFFF)
				TECH_PERM(0xFFFFFFFF)
				USER_PERM(0xFFFFFFFF)
				"
			::= { compassParameters 21 }

		
		-- 1.3.6.1.4.1.16215.1.16.2.18.1.22
		postTiltDataRoll OBJECT-TYPE
			SYNTAX Integer32
			MAX-ACCESS read-only
			STATUS current
			DESCRIPTION
				"Post Tilt Data Roll
				InDB = NO
				ELBIT_PERM(0xFFFFFFFF)
				ADMIN_PERM(0xFFFFFFFF)
				TECH_PERM(0xFFFFFFFF)
				USER_PERM(0xFFFFFFFF)"
			::= { compassParameters 22 }

		
		-- 1.3.6.1.4.1.16215.1.16.2.18.1.23
		tiltDataTempParametersFactor OBJECT-TYPE
			SYNTAX Integer32
			MAX-ACCESS read-only
			STATUS current
			DESCRIPTION
				"Tilt data Temp Use factor multiply or Divide
				InDB = NO
				ELBIT_PERM(0xFFFFFFFF)
				ADMIN_PERM(0xFFFFFFFF)
				TECH_PERM(0xFFFFFFFF)
				USER_PERM(0xFFFFFFFF)"
			::= { compassParameters 23 }

		
		-- 1.3.6.1.4.1.16215.1.16.2.18.1.24
		tiltDataTempFactor OBJECT-TYPE
			SYNTAX Integer32
			MAX-ACCESS read-only
			STATUS current
			DESCRIPTION
				"Tilt data Use factor 
				InDB = NO
				ELBIT_PERM(0xFFFFFFFF)
				ADMIN_PERM(0xFFFFFFFF)
				TECH_PERM(0xFFFFFFFF)
				USER_PERM(0xFFFFFFFF)"
			::= { compassParameters 24 }

		
		-- 1.3.6.1.4.1.16215.1.16.2.18.1.25
		postTiltDataTemp OBJECT-TYPE
			SYNTAX Integer32
			MAX-ACCESS read-only
			STATUS current
			DESCRIPTION
				"Post Tilt data temp
				InDB = NO
				ELBIT_PERM(0xFFFFFFFF)
				ADMIN_PERM(0xFFFFFFFF)
				TECH_PERM(0xFFFFFFFF)
				USER_PERM(0xFFFFFFFF)"
			::= { compassParameters 25 }

		
		-- 1.3.6.1.4.1.16215.1.16.2.18.2
		antennaRotatorStatus OBJECT IDENTIFIER ::= { antennaParameters 2 }

		
		-- 1.3.6.1.4.1.16215.1.16.2.18.2.1
		getAntRotStatus OBJECT-TYPE
			SYNTAX TypeOnOff
			MAX-ACCESS read-write
			STATUS current
			DESCRIPTION
				"Get Antenna Rotator Status
				InDB = NO
				ELBIT_PERM(0xFFFFFFFF)
				ADMIN_PERM(0xFFFFFFFF)
				TECH_PERM(0xFFFFFFFF)
				USER_PERM(0xFFFFFFFF)"
			::= { antennaRotatorStatus 1 }

		
		-- 1.3.6.1.4.1.16215.1.16.2.18.2.2
		readSntRotStatus OBJECT-TYPE
			SYNTAX TypeOnOff
			MAX-ACCESS read-write
			STATUS current
			DESCRIPTION
				"Read Antenna Rotator Status
				InDB = NO
				ELBIT_PERM(0xFFFFFFFF)
				ADMIN_PERM(0xFFFFFFFF)
				TECH_PERM(0xFFFFFFFF)
				USER_PERM(0xFFFFFFFF)"
			::= { antennaRotatorStatus 2 }

		
		-- 1.3.6.1.4.1.16215.1.16.2.18.2.3
		lastCommandExecuted OBJECT-TYPE
			SYNTAX OCTET STRING
			MAX-ACCESS read-only
			STATUS current
			DESCRIPTION
				"Last Command Executed Prior to this command
				InDB = NO
				InDB = NO
				ELBIT_PERM(0xFFFFFFFF)
				ADMIN_PERM(0xFFFFFFFF)
				TECH_PERM(0xFFFFFFFF)
				USER_PERM(0xFFFFFFFF)
				"
			::= { antennaRotatorStatus 3 }

		
		-- 1.3.6.1.4.1.16215.1.16.2.18.2.4
		lastCommandState OBJECT-TYPE
			SYNTAX TypeCommandExecutionStatus
			MAX-ACCESS read-only
			STATUS current
			DESCRIPTION
				"Last Command Execution State
				InDB = NO
				ELBIT_PERM(0xFFFFFFFF)
				ADMIN_PERM(0xFFFFFFFF)
				TECH_PERM(0xFFFFFFFF)
				USER_PERM(0xFFFFFFFF)"
			::= { antennaRotatorStatus 4 }
-- Current 
		
		-- 1.3.6.1.4.1.16215.1.16.2.18.2.5
		mainHwUnitStatus OBJECT-TYPE
			SYNTAX OCTET STRING
			MAX-ACCESS read-only
			STATUS current
			DESCRIPTION
				"Hw Revison 
				InDB = NO
				ELBIT_PERM(0xFFFFFFFF)
				ADMIN_PERM(0xFFFFFFFF)
				TECH_PERM(0xFFFFFFFF)
				USER_PERM(0xFFFFFFFF)"
			::= { antennaRotatorStatus 5 }

		
		-- 1.3.6.1.4.1.16215.1.16.2.18.2.6
		getAntRotVersion OBJECT-TYPE
			SYNTAX TypeOnOff
			MAX-ACCESS read-write
			STATUS current
			DESCRIPTION
				"Get Antenna Rotator Versions
				InDB = NO
				ELBIT_PERM(0xFFFFFFFF)
				ADMIN_PERM(0xFFFFFFFF)
				TECH_PERM(0xFFFFFFFF)
				USER_PERM(0xFFFFFFFF)"
			::= { antennaRotatorStatus 6 }

		
		-- 1.3.6.1.4.1.16215.1.16.2.18.2.7
		antennaRotSwVersion OBJECT-TYPE
			SYNTAX OCTET STRING
			MAX-ACCESS read-only
			STATUS current
			DESCRIPTION
				"Antenna SW Version
				InDB = NO
				ELBIT_PERM(0xFFFFFFFF)
				ADMIN_PERM(0xFFFFFFFF)
				TECH_PERM(0xFFFFFFFF)
				USER_PERM(0xFFFFFFFF)"
			::= { antennaRotatorStatus 7 }

		
		-- 1.3.6.1.4.1.16215.1.16.2.18.2.8
		antennaRotHwVersion OBJECT-TYPE
			SYNTAX OCTET STRING
			MAX-ACCESS read-only
			STATUS current
			DESCRIPTION
				"Antenna Rotator HW Version
				InDB = NO
				ELBIT_PERM(0xFFFFFFFF)
				ADMIN_PERM(0xFFFFFFFF)
				TECH_PERM(0xFFFFFFFF)
				USER_PERM(0xFFFFFFFF)"
			::= { antennaRotatorStatus 8 }

		
		-- 1.3.6.1.4.1.16215.1.16.2.18.2.9
		azmimuthMotorSwVersion OBJECT-TYPE
			SYNTAX OCTET STRING
			MAX-ACCESS read-only
			STATUS current
			DESCRIPTION
				"azimuth motor SW Version
				InDB = NO
				ELBIT_PERM(0xFFFFFFFF)
				ADMIN_PERM(0xFFFFFFFF)
				TECH_PERM(0xFFFFFFFF)
				USER_PERM(0xFFFFFFFF)"
			::= { antennaRotatorStatus 9 }

		
		-- 1.3.6.1.4.1.16215.1.16.2.18.2.10
		elavationMotorSwVersion OBJECT-TYPE
			SYNTAX OCTET STRING
			MAX-ACCESS read-only
			STATUS current
			DESCRIPTION
				"elavation motor SW Version
				InDB = NO
				ELBIT_PERM(0xFFFFFFFF)
				ADMIN_PERM(0xFFFFFFFF)
				TECH_PERM(0xFFFFFFFF)
				USER_PERM(0xFFFFFFFF)"
			::= { antennaRotatorStatus 10 }

		
		-- 1.3.6.1.4.1.16215.1.16.2.18.3
		antennaRotatorScanPamameters OBJECT IDENTIFIER ::= { antennaParameters 3 }

		
		-- 1.3.6.1.4.1.16215.1.16.2.18.3.1
		setInitGimbalScan OBJECT-TYPE
			SYNTAX TypeGimabl
			MAX-ACCESS read-write
			STATUS current
			DESCRIPTION
				"Set Initial Gimbal Scan
				InDB = NO
				ELBIT_PERM(0xFFFFFFFF)
				ADMIN_PERM(0xFFFFFFFF)
				TECH_PERM(0xFFFFFFFF)
				USER_PERM(0xFFFFFFFF)"
			::= { antennaRotatorScanPamameters 1 }

		
		-- 1.3.6.1.4.1.16215.1.16.2.18.3.2
		scanningAzimuthLimit OBJECT-TYPE
			SYNTAX TypeAzimithscanning
			UNITS "Degrrees"
			MAX-ACCESS read-write
			STATUS current
			DESCRIPTION
				"Azimuth limit scann
				InDB = NO
				ELBIT_PERM(0xFFFFFFFF)
				ADMIN_PERM(0xFFFFFFFF)
				TECH_PERM(0xFFFFFFFF)
				USER_PERM(0xFFFFFFFF)"
			::= { antennaRotatorScanPamameters 2 }

		
		-- 1.3.6.1.4.1.16215.1.16.2.18.3.3
		scanningElevationLimit OBJECT-TYPE
			SYNTAX TypeScanningElevation
			UNITS "Degrrees"
			MAX-ACCESS read-write
			STATUS current
			DESCRIPTION
				"Elevatin limit scann
				InDB = NO
				ELBIT_PERM(0xFFFFFFFF)
				ADMIN_PERM(0xFFFFFFFF)
				TECH_PERM(0xFFFFFFFF)
				USER_PERM(0xFFFFFFFF)"
			::= { antennaRotatorScanPamameters 3 }

		
		-- 1.3.6.1.4.1.16215.1.16.2.18.3.4
		dealyBeforeStart OBJECT-TYPE
			SYNTAX TypeDelayScan
			MAX-ACCESS read-write
			STATUS current
			DESCRIPTION
				"Delay Before start scan
				InDB = NO
				ELBIT_PERM(0xFFFFFFFF)
				ADMIN_PERM(0xFFFFFFFF)
				TECH_PERM(0xFFFFFFFF)
				USER_PERM(0xFFFFFFFF)"
			::= { antennaRotatorScanPamameters 4 }

		
		-- 1.3.6.1.4.1.16215.1.16.2.18.3.5
		initalAzimuthScanDirection OBJECT-TYPE
			SYNTAX TypeAzimuthScanDirection
			MAX-ACCESS read-write
			STATUS current
			DESCRIPTION
				"Initial Azimuth Scanning Direction
				InDB = NO
				ELBIT_PERM(0xFFFFFFFF)
				ADMIN_PERM(0xFFFFFFFF)
				TECH_PERM(0xFFFFFFFF)
				USER_PERM(0xFFFFFFFF)"
			::= { antennaRotatorScanPamameters 5 }

		
		-- 1.3.6.1.4.1.16215.1.16.2.18.3.6
		initalElavationScanDirection OBJECT-TYPE
			SYNTAX TypeElavationScanDirection
			MAX-ACCESS read-write
			STATUS current
			DESCRIPTION
				"Initial Elavation Scanning Direction
				InDB = NO
				ELBIT_PERM(0xFFFFFFFF)
				ADMIN_PERM(0xFFFFFFFF)
				TECH_PERM(0xFFFFFFFF)
				USER_PERM(0xFFFFFFFF)"
			::= { antennaRotatorScanPamameters 6 }

		
		-- 1.3.6.1.4.1.16215.1.16.2.18.3.7
		scanSessionLimitTime OBJECT-TYPE
			SYNTAX TypeScanTimeLimit
			MAX-ACCESS read-write
			STATUS current
			DESCRIPTION
				"Scanning Time Limit
				can be set from 10 seconds to 998 seconds
				if value = 999 means that scan for ever until stopped
				InDB = NO
				ELBIT_PERM(0xFFFFFFFF)
				ADMIN_PERM(0xFFFFFFFF)
				TECH_PERM(0xFFFFFFFF)
				USER_PERM(0xFFFFFFFF)"
			::= { antennaRotatorScanPamameters 7 }

		
		-- 1.3.6.1.4.1.16215.1.16.2.18.3.8
		rotationSpeed OBJECT-TYPE
			SYNTAX TypeScanninSpeed
			MAX-ACCESS read-write
			STATUS current
			DESCRIPTION
				"Set Rotation speed in scan
				InDB = NO
				ELBIT_PERM(0xFFFFFFFF)
				ADMIN_PERM(0xFFFFFFFF)
				TECH_PERM(0xFFFFFFFF)
				USER_PERM(0xFFFFFFFF)"
			::= { antennaRotatorScanPamameters 8 }

		
		-- 1.3.6.1.4.1.16215.1.16.2.18.4
		antenna1RotatorExist OBJECT-TYPE
			SYNTAX TypeANtenatExist
			MAX-ACCESS read-only
			STATUS current
			DESCRIPTION
				"Check If antenna 1 Rotator Exist
				InDB = NO
				ELBIT_PERM(0xFFFFFFFF)
				ADMIN_PERM(0xFFFFFFFF)
				TECH_PERM(0xFFFFFFFF)
				USER_PERM(0xFFFFFFFF)"
			::= { antennaParameters 4 }

		
		-- 1.3.6.1.4.1.16215.1.16.2.18.5
		antenna2RotatorExist OBJECT-TYPE
			SYNTAX TypeANtenatExist
			MAX-ACCESS read-only
			STATUS current
			DESCRIPTION
				"Check If antenna 2 Rotator Exist
				InDB = NO
				ELBIT_PERM(0xFFFFFFFF)
				ADMIN_PERM(0xFFFFFFFF)
				TECH_PERM(0xFFFFFFFF)
				USER_PERM(0xFFFFFFFF)"
			::= { antennaParameters 5 }

		
		-- 1.3.6.1.4.1.16215.1.16.2.18.6
		setAntenna1RotatorPower OBJECT-TYPE
			SYNTAX TypeAntnnaPowerSupplyState
			MAX-ACCESS read-write
			STATUS current
			DESCRIPTION
				"Set Antenna Rotator  1 Power Supply only if Exist
				InDB = NO
				ELBIT_PERM(0xFFFFFFFF)
				ADMIN_PERM(0xFFFFFFFF)
				TECH_PERM(0xFFFFFFFF)
				USER_PERM(0xFFFFFFFF)"
			::= { antennaParameters 6 }

		
		-- 1.3.6.1.4.1.16215.1.16.2.18.7
		setAntenna2RotatorPower OBJECT-TYPE
			SYNTAX TypeAntnnaPowerSupplyState
			MAX-ACCESS read-write
			STATUS current
			DESCRIPTION
				"Set Antenna Rotator  2 Power Supply only if Exist
				InDB = NO
				ELBIT_PERM(0xFFFFFFFF)
				ADMIN_PERM(0xFFFFFFFF)
				TECH_PERM(0xFFFFFFFF)
				USER_PERM(0xFFFFFFFF)"
			::= { antennaParameters 7 }

		
		-- 1.3.6.1.4.1.16215.1.16.2.18.8
		calibrateAntennaRotate OBJECT-TYPE
			SYNTAX TypeOnOff
			MAX-ACCESS read-write
			STATUS current
			DESCRIPTION
				"Set sntenna Rotator to calibrate it self
				InDB = NO
				ELBIT_PERM(0xFFFFFFFF)
				ADMIN_PERM(0xFFFFFFFF)
				TECH_PERM(0xFFFFFFFF)
				USER_PERM(0xFFFFFFFF)"
			::= { antennaParameters 8 }

		
		-- 1.3.6.1.4.1.16215.1.16.2.18.9
		moveCw OBJECT-TYPE
			SYNTAX TypeOnOff
			MAX-ACCESS read-write
			STATUS current
			DESCRIPTION
				"move Cw steps.
				InDB = NO
				ELBIT_PERM(0xFFFFFFFF)
				ADMIN_PERM(0xFFFFFFFF)
				TECH_PERM(0xFFFFFFFF)
				USER_PERM(0xFFFFFFFF)"
			::= { antennaParameters 9 }

		
		-- 1.3.6.1.4.1.16215.1.16.2.18.10
		moveCCW OBJECT-TYPE
			SYNTAX TypeOnOff
			MAX-ACCESS read-write
			STATUS current
			DESCRIPTION
				"Step CCW.
				InDB = NO
				ELBIT_PERM(0xFFFFFFFF)
				ADMIN_PERM(0xFFFFFFFF)
				TECH_PERM(0xFFFFFFFF)
				USER_PERM(0xFFFFFFFF)"
			::= { antennaParameters 10 }

		
		-- 1.3.6.1.4.1.16215.1.16.2.18.11
		moveUp OBJECT-TYPE
			SYNTAX TypeOnOff
			MAX-ACCESS read-write
			STATUS current
			DESCRIPTION
				"Move up antena.
				InDB = NO
				ELBIT_PERM(0xFFFFFFFF)
				ADMIN_PERM(0xFFFFFFFF)
				TECH_PERM(0xFFFFFFFF)
				USER_PERM(0xFFFFFFFF)"
			::= { antennaParameters 11 }

		
		-- 1.3.6.1.4.1.16215.1.16.2.18.12
		moveDown OBJECT-TYPE
			SYNTAX TypeOnOff
			MAX-ACCESS read-write
			STATUS current
			DESCRIPTION
				"Move Down antena.
				InDB = NO
				ELBIT_PERM(0x00000003)
				ADMIN_PERM(0x00000003)
				TECH_PERM(0x00000003)
				USER_PERM(0x00000003)"
			::= { antennaParameters 12 }

		
		-- 1.3.6.1.4.1.16215.1.16.2.18.13
		stopMoving OBJECT-TYPE
			SYNTAX TypeOnOff
			MAX-ACCESS read-write
			STATUS current
			DESCRIPTION
				"Stop Moving.
				InDB = NO
				ELBIT_PERM(0x00000003)
				ADMIN_PERM(0x00000003)
				TECH_PERM(0x00000003)
				USER_PERM(0x00000003)"
			::= { antennaParameters 13 }

		
		-- 1.3.6.1.4.1.16215.1.16.2.18.14
		startScanning OBJECT-TYPE
			SYNTAX TypeOnOff
			MAX-ACCESS read-write
			STATUS current
			DESCRIPTION
				"Start scanning take time from scanning time
				InDB = NO
				ELBIT_PERM(0x00000003)
				ADMIN_PERM(0x00000003)
				TECH_PERM(0x00000003)
				USER_PERM(0x00000003)"
			::= { antennaParameters 14 }

		
		-- 1.3.6.1.4.1.16215.1.16.2.18.15
		getArAzimuth OBJECT-TYPE
			SYNTAX TypeOnOff
			MAX-ACCESS read-write
			STATUS current
			DESCRIPTION
				"Get AR Azimuth value Command.
				InDB = NO
				ELBIT_PERM(0x00000003)
				ADMIN_PERM(0x00000003)
				TECH_PERM(0x00000003)
				USER_PERM(0x00000003)"
			::= { antennaParameters 15 }

		
		-- 1.3.6.1.4.1.16215.1.16.2.18.16
		arAzimuthValue OBJECT-TYPE
			SYNTAX Integer32
			MAX-ACCESS read-only
			STATUS current
			DESCRIPTION
				"Azimuth Value get from AR
				InDB = NO
				ELBIT_PERM(0x00000003)
				ADMIN_PERM(0x00000003)
				TECH_PERM(0x00000003)
				USER_PERM(0x00000003)"
			::= { antennaParameters 16 }

		
		-- 1.3.6.1.4.1.16215.1.16.2.18.17
		getArElavation OBJECT-TYPE
			SYNTAX TypeOnOff
			MAX-ACCESS read-write
			STATUS current
			DESCRIPTION
				"Get AR Elavation value Command.
				InDB = NO
				ELBIT_PERM(0x00000003)
				ADMIN_PERM(0x00000003)
				TECH_PERM(0x00000003)
				USER_PERM(0x00000003)"
			::= { antennaParameters 17 }

		
		-- 1.3.6.1.4.1.16215.1.16.2.18.18
		arElavationValue OBJECT-TYPE
			SYNTAX Integer32
			MAX-ACCESS read-only
			STATUS current
			DESCRIPTION
				"Ar Elavation Value
				InDB = NO
				ELBIT_PERM(0x00000003)
				ADMIN_PERM(0x00000003)
				TECH_PERM(0x00000003)
				USER_PERM(0x00000003)"
			::= { antennaParameters 18 }

		
		-- 1.3.6.1.4.1.16215.1.16.2.18.19
		getAzimuthElavationValues OBJECT-TYPE
			SYNTAX TypeOnOff
			MAX-ACCESS read-write
			STATUS current
			DESCRIPTION
				"Get AR Azimuth And Elavation values at single command.
				InDB = NO
				ELBIT_PERM(0x00000003)
				ADMIN_PERM(0x00000003)
				TECH_PERM(0x00000003)
				USER_PERM(0x00000003)
				Values Can Be read on arAzimuthValue And getArElavation Oid's"
			::= { antennaParameters 19 }

		
		-- 1.3.6.1.4.1.16215.1.16.2.18.20
		goToAzimuthTargetCmd OBJECT-TYPE
			SYNTAX TypeOnOff
			MAX-ACCESS read-write
			STATUS current
			DESCRIPTION
				"Set Command Azimuth Target
				InDB = NO
				ELBIT_PERM(0x00000003)
				ADMIN_PERM(0x00000003)
				TECH_PERM(0x00000003)
				USER_PERM(0x00000003)"
			::= { antennaParameters 20 }

		
		-- 1.3.6.1.4.1.16215.1.16.2.18.21
		goToAzimuthValue OBJECT-TYPE
			SYNTAX TypeAzimuthValue
			MAX-ACCESS read-write
			STATUS current
			DESCRIPTION
				"Azimuth Value
				InDB = NO
				ELBIT_PERM(0x00000003)
				ADMIN_PERM(0x00000003)
				TECH_PERM(0x00000003)
				USER_PERM(0x00000003)"
			::= { antennaParameters 21 }

		
		-- 1.3.6.1.4.1.16215.1.16.2.18.22
		goToElavationTargetCmd OBJECT-TYPE
			SYNTAX TypeOnOff
			MAX-ACCESS read-write
			STATUS current
			DESCRIPTION
				"Set Command Elavation Target
				InDB = NO
				ELBIT_PERM(0x00000003)
				ADMIN_PERM(0x00000003)
				TECH_PERM(0x00000003)
				USER_PERM(0x00000003)."
			::= { antennaParameters 22 }

		
		-- 1.3.6.1.4.1.16215.1.16.2.18.23
		goToElavationValue OBJECT-TYPE
			SYNTAX TypeElavationValue
			MAX-ACCESS read-write
			STATUS current
			DESCRIPTION
				"Elavation Value
				InDB = NO
				ELBIT_PERM(0x00000003)
				ADMIN_PERM(0x00000003)
				TECH_PERM(0x00000003)
				USER_PERM(0x00000003)"
			::= { antennaParameters 23 }

		
		-- 1.3.6.1.4.1.16215.1.16.2.18.24
		rssiMaxValue OBJECT-TYPE
			SYNTAX Integer32
			MAX-ACCESS read-only
			STATUS current
			DESCRIPTION
				"Rssi Maximum Value That found in Scan
				InDB = NO
				ELBIT_PERM(0x0FFFFFFFF)
				ADMIN_PERM(0x0FFFFFFFF)
				TECH_PERM(0x0FFFFFFFF)
				USER_PERM(0x0FFFFFFFF)"
			::= { antennaParameters 24 }

		
		-- 1.3.6.1.4.1.16215.1.16.2.18.25
		degreeOfRssiMaxValue OBJECT-TYPE
			SYNTAX Integer32
			MAX-ACCESS read-only
			STATUS current
			DESCRIPTION
				"The Degree of Rssi Maximum Value That found in Scan
				InDB = NO
				ELBIT_PERM(0x0FFFFFFFF)
				ADMIN_PERM(0x0FFFFFFFF)
				TECH_PERM(0x0FFFFFFFF)
				USER_PERM(0x0FFFFFFFF)"
			::= { antennaParameters 25 }

		
		-- 1.3.6.1.4.1.16215.1.16.2.18.26
		rssiMaxValueModemLoc OBJECT-TYPE
			SYNTAX Integer32
			MAX-ACCESS read-only
			STATUS current
			DESCRIPTION
				"Rssi Maximum Value That found in Scan when BroadComm Modem is Loc
				InDB = NO
				ELBIT_PERM(0x0FFFFFFFF)
				ADMIN_PERM(0x0FFFFFFFF)
				TECH_PERM(0x0FFFFFFFF)
				USER_PERM(0x0FFFFFFFF)"
			::= { antennaParameters 26 }

		
		-- 1.3.6.1.4.1.16215.1.16.2.18.27
		degreeOfRssiMaxValueModemLoc OBJECT-TYPE
			SYNTAX Integer32
			MAX-ACCESS read-only
			STATUS current
			DESCRIPTION
				"The Degree of Rssi Maximum Value That found in Scan When BroadCom Modem Is loc
				InDB = NO
				ELBIT_PERM(0x0FFFFFFFF)
				ADMIN_PERM(0x0FFFFFFFF)
				TECH_PERM(0x0FFFFFFFF)
				USER_PERM(0x0FFFFFFFF)"
			::= { antennaParameters 27 }

		
		-- 1.3.6.1.4.1.16215.1.16.2.18.28
		snrMaxValueModemLoc OBJECT-TYPE
			SYNTAX INTEGER (-70..-20)
			MAX-ACCESS read-only
			STATUS current
			DESCRIPTION
				"SNR Maximum Value That found in Scan when BroadComm Modem is Loc Value is multipeld by 100 to get 2 point of accurate of float
				InDB = NO
				ELBIT_PERM(0x0FFFFFFFF)
				ADMIN_PERM(0x0FFFFFFFF)
				TECH_PERM(0x0FFFFFFFF)
				USER_PERM(0x0FFFFFFFF)"
			::= { antennaParameters 28 }

		
		-- 1.3.6.1.4.1.16215.1.16.2.18.29
		degreeOfSnrMaxValueModemLoc OBJECT-TYPE
			SYNTAX Integer32
			MAX-ACCESS read-only
			STATUS current
			DESCRIPTION
				"The Degree of SNR Maximum Value That found in Scan When BroadCom Modem Is loc
				InDB = NO
				ELBIT_PERM(0x0FFFFFFFF)
				ADMIN_PERM(0x0FFFFFFFF)
				TECH_PERM(0x0FFFFFFFF)
				USER_PERM(0x0FFFFFFFF)"
			::= { antennaParameters 29 }

		
		-- 1.3.6.1.4.1.16215.1.16.2.18.30
		scanStatus OBJECT-TYPE
			SYNTAX TypeOnOff
			MAX-ACCESS read-only
			STATUS current
			DESCRIPTION
				"Scan Status.
				The State of scan 1 - not scan
				                  2 - in scan 
				InDB = NO
				
				"
			::= { antennaParameters 30 }       
		-- 1.3.6.1.4.1.16215.1.16.2.18.31
		forceAntennaRotatorSWupdate OBJECT-TYPE
			SYNTAX TypeForceUpdate
			MAX-ACCESS read-write
			STATUS current
			DESCRIPTION
				"Force Update.
				0 - no update
				1 - update "
			::= { antennaParameters 31 } 
			
	-- 1.3.6.1.4.1.16215.1.16.2.18.32
		 	getAntennaStatus OBJECT-TYPE
			SYNTAX TypeAntennaRotatorStatus
			MAX-ACCESS read-only
			STATUS current
			DESCRIPTION
				"Antenna Status.
				AR_STATUS_IDLE =1,
 				AR_STATUS_EXE =2,
 				AR_STATUS_ABORT =3,
				AR_STATUS_QUEUED =4,
				AR_STATUS_ERROR =5,
				AR_STATUS_BOOT =6 "
			::= { antennaParameters 32 } 
			
		-- 1.3.6.1.4.1.16215.1.16.2.18.33
		 	azimuthSpeed OBJECT-TYPE
			SYNTAX TypeAntennaSpeed
			MAX-ACCESS read-write
			STATUS current
			DESCRIPTION
			"001 - Speed 1
			 010 - Speed 2
		     011 -  Speed 3
			 100 -  Speed 4"
			::= { antennaParameters 33 } 		
			
	
			-- 1.3.6.1.4.1.16215.1.16.2.18.34
		 	elevatioSpeed OBJECT-TYPE
			SYNTAX TypeAntennaSpeed
			MAX-ACCESS read-write
			STATUS current
			DESCRIPTION
			"001 - Speed 1
			 010 - Speed 2
		     011 -  Speed 3
			 100 -  Speed 4"
			::= { antennaParameters 34 } 
			
			
			-- 1.3.6.1.4.1.16215.1.16.2.18.35
		 	antenna1Polarization OBJECT-TYPE
			SYNTAX INTEGER (1..2)
			MAX-ACCESS read-write
			STATUS current
			DESCRIPTION
			"2- vertical
			1- horizontal"
			::= { antennaParameters 35 }    
			-- 1.3.6.1.4.1.16215.1.16.2.18.36  
			
		 	antenna2Polarization OBJECT-TYPE
			SYNTAX INTEGER (1..2)
			MAX-ACCESS read-write
			STATUS current
			DESCRIPTION
			"2- vertical
			1- horizontal"
			::= { antennaParameters 36 } 



	-- 1.3.6.1.4.1.16215.1.16.2.19
		rtcSettings OBJECT IDENTIFIER ::= { odu 19 }

		
		-- 1.3.6.1.4.1.16215.1.16.2.19.1
		setTime OBJECT-TYPE
			SYNTAX OCTET STRING (SIZE (0..255))
			MAX-ACCESS read-write
			STATUS current
			DESCRIPTION
				"Time of Dat in HH:MM:SS format.
				InDB = NO
				ELBIT_PERM(0xFFFFFFFF)
				ADMIN_PERM(0xFFFFFFFF)
				TECH_PERM(0xFFFFFFFF)
				USER_PERM(0xFFFFFFFF)
				"
			::= { rtcSettings 1 }

		
		-- 1.3.6.1.4.1.16215.1.16.2.19.2
		setDate OBJECT-TYPE
			SYNTAX OCTET STRING (SIZE (0..255))
			MAX-ACCESS read-write
			STATUS current
			DESCRIPTION
				"Date of year in format in YYYY:MM:DD format.
				YYYY - current year
				MM   - month from 1 to 12
				DD   - day of month from 1 to 31
				
				InDB = NO
				ELBIT_PERM(0xFFFFFFFF)
				ADMIN_PERM(0xFFFFFFFF)
				TECH_PERM(0xFFFFFFFF)
				USER_PERM(0xFFFFFFFF)
				"
			::= { rtcSettings 2 }

		
		-- 1.3.6.1.4.1.16215.1.16.2.20
		grxkeys OBJECT IDENTIFIER ::= { odu 20 }

		
		-- 1.3.6.1.4.1.16215.1.16.2.20.1
		fixfrequencykeys OBJECT IDENTIFIER ::= { grxkeys 1 }

		
		-- 1.3.6.1.4.1.16215.1.16.2.20.1.1
		fixfrequencykeyCRC OBJECT-TYPE
			SYNTAX Integer32
			MAX-ACCESS read-only
			STATUS current
			DESCRIPTION
				"CRC code for fix data key
				InDB = NO
				ELBIT_PERM(0xFFFFFFFF)
				ADMIN_PERM(0xFFFFFFFF)
				TECH_PERM(0xFFFFFFFF)
				USER_PERM(0xFFFFFFFF)
				"
			::= { fixfrequencykeys 1 }

		
		-- 1.3.6.1.4.1.16215.1.16.2.20.1.2
		fixfrequencykey OBJECT-TYPE
			SYNTAX OCTET STRING (SIZE (0..31))
			MAX-ACCESS read-write
			STATUS current
			DESCRIPTION
				"Data Key Value
				InDB = NO
				InDB = NO
				ELBIT_PERM(0xFFFFFFFF)
				ADMIN_PERM(0xFFFFFFFF)
				TECH_PERM(0xFFFFFFFF)
				USER_PERM(0xFFFFFFFF)
				"
			::= { fixfrequencykeys 2 }

		
		-- 1.3.6.1.4.1.16215.1.16.2.20.1.3
		fixdatakeyCRC OBJECT-TYPE
			SYNTAX Integer32
			MAX-ACCESS read-write
			STATUS current
			DESCRIPTION
				"InDB = NO
				ELBIT_PERM(0xFFFFFFFF)
				ADMIN_PERM(0xFFFFFFFF)
				TECH_PERM(0xFFFFFFFF)
				USER_PERM(0xFFFFFFFF)
				"
			::= { fixfrequencykeys 3 }

		
		-- 1.3.6.1.4.1.16215.1.16.2.20.1.4
		fixdatakey OBJECT-TYPE
			SYNTAX OCTET STRING (SIZE (0..31))
			MAX-ACCESS read-write
			STATUS current
			DESCRIPTION
				"InDB = NO
				ELBIT_PERM(0xFFFFFFFF)
				ADMIN_PERM(0xFFFFFFFF)
				TECH_PERM(0xFFFFFFFF)
				USER_PERM(0xFFFFFFFF)
				"
			::= { fixfrequencykeys 4 }

		
		-- 1.3.6.1.4.1.16215.1.16.2.20.2
		hopfrequencykeys OBJECT IDENTIFIER ::= { grxkeys 2 }

		
		-- 1.3.6.1.4.1.16215.1.16.2.20.2.1
		hopfrequencykeyCRC OBJECT-TYPE
			SYNTAX Integer32
			MAX-ACCESS read-write
			STATUS current
			DESCRIPTION
				"InDB = NO
				ELBIT_PERM(0xFFFFFFFF)
				ADMIN_PERM(0xFFFFFFFF)
				TECH_PERM(0xFFFFFFFF)
				USER_PERM(0xFFFFFFFF)
				"
			::= { hopfrequencykeys 1 }

		
		-- 1.3.6.1.4.1.16215.1.16.2.20.2.2
		hopfrequencykey OBJECT-TYPE
			SYNTAX OCTET STRING (SIZE (0..31))
			MAX-ACCESS read-write
			STATUS current
			DESCRIPTION
				"InDB = NO
				ELBIT_PERM(0xFFFFFFFF)
				ADMIN_PERM(0xFFFFFFFF)
				TECH_PERM(0xFFFFFFFF)
				USER_PERM(0xFFFFFFFF)
				"
			::= { hopfrequencykeys 2 }

		
		-- 1.3.6.1.4.1.16215.1.16.2.20.2.3
		hopdatakeyCRC OBJECT-TYPE
			SYNTAX Integer32
			MAX-ACCESS read-write
			STATUS current
			DESCRIPTION
				"InDB = NO
				ELBIT_PERM(0xFFFFFFFF)
				ADMIN_PERM(0xFFFFFFFF)
				TECH_PERM(0xFFFFFFFF)
				USER_PERM(0xFFFFFFFF)
				"
			::= { hopfrequencykeys 3 }

		
		-- 1.3.6.1.4.1.16215.1.16.2.20.2.4
		hopdatakey OBJECT-TYPE
			SYNTAX OCTET STRING (SIZE (0..31))
			MAX-ACCESS read-write
			STATUS current
			DESCRIPTION
				"InDB = NO
				ELBIT_PERM(0xFFFFFFFF)
				ADMIN_PERM(0xFFFFFFFF)
				TECH_PERM(0xFFFFFFFF)
				USER_PERM(0xFFFFFFFF)
				"
			::= { hopfrequencykeys 4 }

		
		-- 1.3.6.1.4.1.16215.1.16.2.21
		agcControl OBJECT IDENTIFIER ::= { odu 21 }
-- Handles AGC parametrs
-- 
		
		-- 1.3.6.1.4.1.16215.1.16.2.21.1
		agcWorkingMode OBJECT-TYPE
			SYNTAX TypeAgcWorkingMode
			MAX-ACCESS read-write
			STATUS current
			DESCRIPTION
				"Agc Working mode Manul Or Automatic.
				DEFVAL { 0x1 }
				InDB = YES
				TypeInDB=UCHAR
				ELBIT_PERM(0x00000003)
				ADMIN_PERM(0x00000003)
				TECH_PERM(0x00000003)
				USER_PERM(0x00000003)"
			::= { agcControl 1 }

		
		-- 1.3.6.1.4.1.16215.1.16.2.21.2
		rSSImesureSRC OBJECT-TYPE
			SYNTAX TypeMesureSrc
			MAX-ACCESS read-write
			STATUS current
			DESCRIPTION
				"Rssi Mesure Source From IF or Base Band.
				DEFVAL { 0x1 }
				InDB = YES
				TypeInDB=UCHAR
				ELBIT_PERM(0x00000003)
				ADMIN_PERM(0x00000003)
				TECH_PERM(0x00000003)
				USER_PERM(0x00000003)"
			::= { agcControl 2 }

		
		-- 1.3.6.1.4.1.16215.1.16.2.21.3
		attenuatortouse OBJECT-TYPE
			SYNTAX TypeAttenToUse
			MAX-ACCESS read-write
			STATUS current
			DESCRIPTION
				"Wich Attenuator to use VVA or DCA.
				DEFVAL { 0x1 }
				InDB = YES
				TypeInDB=UCHAR
				ELBIT_PERM(0x00000003)
				ADMIN_PERM(0x00000003)
				TECH_PERM(0x00000003)
				USER_PERM(0x00000003)"
			::= { agcControl 3 }

		
		-- 1.3.6.1.4.1.16215.1.16.2.21.4
		lna1State OBJECT-TYPE
			SYNTAX TypeLnaOnOff
			MAX-ACCESS read-write
			STATUS current
			DESCRIPTION
				"LNA State OF of ON.
				DEFVAL { 0x1 }
				InDB = YES
				TypeInDB=UCHAR
				ELBIT_PERM(0x00000003)
				ADMIN_PERM(0x00000003)
				TECH_PERM(0x00000003)
				USER_PERM(0x00000003)."
			::= { agcControl 4 }

		
		-- 1.3.6.1.4.1.16215.1.16.2.21.5
		lna2State OBJECT-TYPE
			SYNTAX TypeLnaOnOff
			MAX-ACCESS read-write
			STATUS current
			DESCRIPTION
				"LNA State OF of ON.
				DEFVAL { 0x1 }
				InDB = YES
				TypeInDB=UCHAR
				ELBIT_PERM(0x00000003)
				ADMIN_PERM(0x00000003)
				TECH_PERM(0x00000003)
				USER_PERM(0x00000003)."
			::= { agcControl 5 }

		
		-- 1.3.6.1.4.1.16215.1.16.2.21.6
		rssiMesureState OBJECT-TYPE
			SYNTAX TypeRssiMesureState
			MAX-ACCESS read-write
			STATUS current
			DESCRIPTION
				"Start Stop RSSI Mesures.
				DEFVAL { 0x0 }
				InDB = YES
				TypeInDB=UCHAR
				ELBIT_PERM(0x00000003)
				ADMIN_PERM(0x00000003)
				TECH_PERM(0x00000003)
				USER_PERM(0x00000003).
				"
			::= { agcControl 6 }

		
		-- 1.3.6.1.4.1.16215.1.16.2.21.7
		mesureStepSize OBJECT-TYPE
			SYNTAX TypeStepSize
			MAX-ACCESS read-write
			STATUS current
			DESCRIPTION
				"RSSI mesure Step Size.
				DEFVAL { 0x1 }
				InDB = YES
				TypeInDB=UCHAR
				ELBIT_PERM(0x00000003)
				ADMIN_PERM(0x00000003)
				TECH_PERM(0x00000003)
				USER_PERM(0x00000003)."
			::= { agcControl 7 }

		
		-- 1.3.6.1.4.1.16215.1.16.2.21.8
		alcStepSize OBJECT-TYPE
			SYNTAX TypeStepSize
			MAX-ACCESS read-write
			STATUS current
			DESCRIPTION
				"ALCstep Size.
				DEFVAL { 0x0 }
				InDB = YES
				TypeInDB=UCHAR
				ELBIT_PERM(0x00000003)
				ADMIN_PERM(0x00000003)
				TECH_PERM(0x00000003)
				USER_PERM(0x00000003)."
			::= { agcControl 8 }

		
		-- 1.3.6.1.4.1.16215.1.16.2.21.9
		vvaDCACtrlSelect OBJECT-TYPE
			SYNTAX TypeATenuatorCtrlSelect
			MAX-ACCESS read-write
			STATUS current
			DESCRIPTION
				"Select wich wich choose the Attenuator Sw/Hw
				DEFVAL { 0x0 }
				InDB = YES
				TypeInDB=UCHAR
				ELBIT_PERM(0x00000003)
				ADMIN_PERM(0x00000003)
				TECH_PERM(0x00000003)
				USER_PERM(0x00000003)."
			::= { agcControl 9 }

		
		-- 1.3.6.1.4.1.16215.1.16.2.21.10
		agcChangeThreshold OBJECT-TYPE
			SYNTAX Integer32 (0..255)
			MAX-ACCESS read-write
			STATUS current
			DESCRIPTION
				"Select selecet AGC cheange threshold
				DEFVAL { 0x0 }
				InDB = NO
				TypeInDB=UCHAR
				ELBIT_PERM(0x0000FFFF)
				ADMIN_PERM(0x0000FFFF)
				TECH_PERM(0x0000FFFF)
				USER_PERM(0x0000FFFF)."
			::= { agcControl 10 }

		
		-- 1.3.6.1.4.1.16215.1.16.2.21.11
		agcVVA1Manual OBJECT-TYPE
			SYNTAX TypeVVAValue
			MAX-ACCESS read-write
			STATUS current
			DESCRIPTION
				"Select selecet AGC VVA1 Manual
				Same AS VVA5B
				DEFVAL { 554 }
				InDB = NO
				TypeInDB=UCHAR
				ELBIT_PERM(0x0000FFFF)
				ADMIN_PERM(0x0000FFFF)
				TECH_PERM(0x0000FFFF)
				USER_PERM(0x0000FFFF)."
			::= { agcControl 11 }

		
		-- 1.3.6.1.4.1.16215.1.16.2.21.12
		agcVVA2Manual OBJECT-TYPE
			SYNTAX TypeVVAValue
			MAX-ACCESS read-write
			STATUS current
			DESCRIPTION
				"Select selecet AGC VVA2 Manual
				Same AS VVA4B
				DEFVAL { 1023 }
				InDB = NO
				TypeInDB=UCHAR
				ELBIT_PERM(0x0000FFFF)
				ADMIN_PERM(0x0000FFFF)
				TECH_PERM(0x0000FFFF)
				USER_PERM(0x0000FFFF)."
			::= { agcControl 12 }

		
		-- 1.3.6.1.4.1.16215.1.16.2.21.13
		agcVVA3Manual OBJECT-TYPE
			SYNTAX TypeVVAValue
			MAX-ACCESS read-write
			STATUS current
			DESCRIPTION
				"Select selecet AGC VVA3 Manual
				Same AS VVA3B
				DEFVAL { 1023 }
				InDB = NO
				TypeInDB=UCHAR
				ELBIT_PERM(0x0000FFFF)
				ADMIN_PERM(0x0000FFFF)
				TECH_PERM(0x0000FFFF)
				USER_PERM(0x0000FFFF)."
			::= { agcControl 13 }

		
		-- 1.3.6.1.4.1.16215.1.16.2.21.14
		agcDCAManual OBJECT-TYPE
			SYNTAX Integer32 (0..255)
			MAX-ACCESS read-write
			STATUS current
			DESCRIPTION
				"Select selecet AGC DCA Manual
				DEFVAL { 0x0 }
				InDB = NO
				TypeInDB=UCHAR
				ELBIT_PERM(0x0000FFFF)
				ADMIN_PERM(0x0000FFFF)
				TECH_PERM(0x0000FFFF)
				USER_PERM(0x0000FFFF)."
			::= { agcControl 14 }
		-- 1.3.6.1.4.1.16215.1.16.2.21.11

		agcVVA5BManual OBJECT-TYPE
			SYNTAX TypeVVAValue
			MAX-ACCESS read-write
			STATUS current
			DESCRIPTION
				"Select selecet AGC VVA1 Manual
				Same As agcVVA1Manual
				DEFVAL { 554 }
				InDB = NO
				TypeInDB=UCHAR
				ELBIT_PERM(0x0000FFFF)
				ADMIN_PERM(0x0000FFFF)
				TECH_PERM(0x0000FFFF)
				USER_PERM(0x0000FFFF)."
			::= { agcControl 15 }

		
		-- 1.3.6.1.4.1.16215.1.16.2.21.12
		agcVVA4BManual OBJECT-TYPE
			SYNTAX TypeVVAValue
			MAX-ACCESS read-write
			STATUS current
			DESCRIPTION
				"Select selecet AGC VVA2 Manual
				Same As agcVVA2Manual
				DEFVAL { 1023 }
				InDB = NO
				TypeInDB=UCHAR
				ELBIT_PERM(0x0000FFFF)
				ADMIN_PERM(0x0000FFFF)
				TECH_PERM(0x0000FFFF)
				USER_PERM(0x0000FFFF)."
			::= { agcControl 16 }

		
		-- 1.3.6.1.4.1.16215.1.16.2.21.13
		agcVVA3BManual OBJECT-TYPE
			SYNTAX TypeVVAValue
			MAX-ACCESS read-write
			STATUS current
			DESCRIPTION
				"Select selecet AGC VVA3 Manual
				Same As agcVVA3Manual
				DEFVAL { 1023 }
				InDB = NO
				TypeInDB=UCHAR
				ELBIT_PERM(0x0000FFFF)
				ADMIN_PERM(0x0000FFFF)
				TECH_PERM(0x0000FFFF)
				USER_PERM(0x0000FFFF)."
			::= { agcControl 17 }

		
		-- 1.3.6.1.4.1.16215.1.16.2.22
		bcmParameters OBJECT IDENTIFIER ::= { odu 22 }

		
		-- 1.3.6.1.4.1.16215.1.16.2.22.1
		broadcomTxIFFreq OBJECT-TYPE
			SYNTAX Integer32
			MAX-ACCESS read-write
			STATUS current
			DESCRIPTION
				"Transmit broadCom If Frequency in x*125Khz.
				DEFVAL { 0x70 }
				InDB = NO
				TypeInDB=UCHAR
				ELBIT_PERM(0x000000FF)
				ADMIN_PERM(0x00000000)
				TECH_PERM(0x000000000)
				USER_PERM(0x000000000)"
			::= { bcmParameters 1 }

		
		-- 1.3.6.1.4.1.16215.1.16.2.22.2
		broadcomTxIFBw OBJECT-TYPE
			SYNTAX Integer32
			MAX-ACCESS read-write
			STATUS current
			DESCRIPTION
				"Transmit broadCom If BandWidh in x*125Khz.
				DEFVAL { 0x30 }
				InDB = NO
				TypeInDB=UCHAR
				ELBIT_PERM(0x000000FF)
				ADMIN_PERM(0x00000000)
				TECH_PERM(0x000000000)
				USER_PERM(0x000000000)"
			::= { bcmParameters 2 }

		
		-- 1.3.6.1.4.1.16215.1.16.2.22.3
		broadcomTxIFOffset OBJECT-TYPE
			SYNTAX Integer32
			MAX-ACCESS read-write
			STATUS current
			DESCRIPTION
				"Transmit broadCom If Offset in case of work In Multi point  in x*125Khz.
				DEFVAL { 0x30 }
				InDB = NO
				TypeInDB=UCHAR
				ELBIT_PERM(0x000000FF)
				ADMIN_PERM(0x00000000)
				TECH_PERM(0x000000000)
				USER_PERM(0x000000000)"
			::= { bcmParameters 3 }

		
		-- 1.3.6.1.4.1.16215.1.16.2.22.4
		broadcomRxIFFreq OBJECT-TYPE
			SYNTAX Integer32
			MAX-ACCESS read-write
			STATUS current
			DESCRIPTION
				"Receive broadCom If Frequency in x*125Khz.
				DEFVAL { 0x70 }
				InDB = NO
				TypeInDB=UCHAR
				ELBIT_PERM(0x000000FF)
				ADMIN_PERM(0x00000000)
				TECH_PERM(0x000000000)
				USER_PERM(0x000000000)"
			::= { bcmParameters 4 }

		
		-- 1.3.6.1.4.1.16215.1.16.2.22.5
		broadcomRxIFBw OBJECT-TYPE
			SYNTAX Integer32
			MAX-ACCESS read-write
			STATUS current
			DESCRIPTION
				"Receive broadCom If BandWidh in x*125Khz.
				DEFVAL { 0x30 }
				InDB = NO
				TypeInDB=UCHAR
				ELBIT_PERM(0x000000FF)
				ADMIN_PERM(0x00000000)
				TECH_PERM(0x000000000)
				USER_PERM(0x000000000)"
			::= { bcmParameters 5 }

		
		-- 1.3.6.1.4.1.16215.1.16.2.22.6
		broadcomRxIFOffset OBJECT-TYPE
			SYNTAX Integer32
			MAX-ACCESS read-write
			STATUS current
			DESCRIPTION
				"Receive broadCom If Offset in case of work In Multi point  in x*125Khz.
				DEFVAL { 0x30 }
				InDB = NO
				TypeInDB=UCHAR
				ELBIT_PERM(0x000000FF)
				ADMIN_PERM(0x00000000)
				TECH_PERM(0x000000000)
				USER_PERM(0x000000000)"
			::= { bcmParameters 6 }

		
		-- 1.3.6.1.4.1.16215.1.16.2.23
		grx8000Counters OBJECT IDENTIFIER ::= { odu 23 }
-- Describes the GRX Life Counter and 
-- Biggest Counter in the System
		
		-- 1.3.6.1.4.1.16215.1.16.2.23.1
		grx8000LifeCounter OBJECT-TYPE
			SYNTAX Integer32
			MAX-ACCESS read-only
			STATUS current
			DESCRIPTION
				"Describes The GRX Life counter Since it came out from Factory.
				DEFVAL { 1}
				InDB = YES
				TypeInDB=ULONG
				ELBIT_PERM(0xFFFFFFFF)
				ADMIN_PERM(0xFFFFFFFF)
				TECH_PERM(0xFFFFFFFF)
				USER_PERM(0xFFFFFFFF)"
			::= { grx8000Counters 1 }

		
		-- 1.3.6.1.4.1.16215.1.16.2.23.2
		grxBiggestCounterInLink OBJECT-TYPE
			SYNTAX Integer32
			MAX-ACCESS read-only
			STATUS current
			DESCRIPTION
				"Describes The Biggest Counter that read from GRX cloud.
				DEFVAL { 1}
				InDB = YES
				TypeInDB=ULONG
				ELBIT_PERM(0xFFFFFFFF)
				ADMIN_PERM(0xFFFFFFFF)
				TECH_PERM(0xFFFFFFFF)
				USER_PERM(0xFFFFFFFF)"
			::= { grx8000Counters 2 }

		
		-- 1.3.6.1.4.1.16215.1.16.2.24
		afeandMacControl OBJECT IDENTIFIER ::= { odu 24 }

		
		-- 1.3.6.1.4.1.16215.1.16.2.24.1
		afeConfigStart OBJECT-TYPE
			SYNTAX TypeCfgStartRegister
			MAX-ACCESS read-write
			STATUS current
			DESCRIPTION
				"InDB = NO
				ELBIT_PERM(0xFFFFFFFF)
				ADMIN_PERM(0x00000000)
				TECH_PERM(0x00000000)
				USER_PERM(0x00000000)"
			::= { afeandMacControl 1 }

		
		-- 1.3.6.1.4.1.16215.1.16.2.24.2
		a2DPowerDownRegister OBJECT IDENTIFIER ::= { afeandMacControl 2 }

		
		-- 1.3.6.1.4.1.16215.1.16.2.24.2.1
		selecetChanA OBJECT-TYPE
			SYNTAX TypeChannelOn
			MAX-ACCESS read-write
			STATUS current
			DESCRIPTION
				"Select Channel A
				0 - Disable Channel
				1 - Enable Channel
				InDB = NO
				ELBIT_PERM(0x0000001F)
				ADMIN_PERM(0x00000000)
				TECH_PERM(0x000000000)
				USER_PERM(0x00000000)"
			::= { a2DPowerDownRegister 1 }

		
		-- 1.3.6.1.4.1.16215.1.16.2.24.2.2
		selecetChanB OBJECT-TYPE
			SYNTAX TypeChannelOn
			MAX-ACCESS read-write
			STATUS current
			DESCRIPTION
				"Select Channel B
				0 - Disable Channel
				1 - Enable Channel
				InDB = NO
				ELBIT_PERM(0x0000001F)
				ADMIN_PERM(0x00000000)
				TECH_PERM(0x000000000)
				USER_PERM(0x00000000)"
			::= { a2DPowerDownRegister 2 }

		
		-- 1.3.6.1.4.1.16215.1.16.2.24.2.3
		selecetChanC OBJECT-TYPE
			SYNTAX TypeChannelOn
			MAX-ACCESS read-write
			STATUS current
			DESCRIPTION
				"Select Channel C
				0 - Disable Channel
				1 - Enable Channel
				InDB = NO
				ELBIT_PERM(0x0000001F)
				ADMIN_PERM(0x00000000)
				TECH_PERM(0x000000000)
				USER_PERM(0x00000000)"
			::= { a2DPowerDownRegister 3 }

		
		-- 1.3.6.1.4.1.16215.1.16.2.24.2.4
		selecetChanD OBJECT-TYPE
			SYNTAX TypeChannelOn
			MAX-ACCESS read-write
			STATUS current
			DESCRIPTION
				"Select Channel D
				0 - Disable Channel
				1 - Enable Channel
				InDB = NO
				ELBIT_PERM(0x0000001F)
				ADMIN_PERM(0x00000000)
				TECH_PERM(0x000000000)
				USER_PERM(0x00000000)"
			::= { a2DPowerDownRegister 4 }

		
		-- 1.3.6.1.4.1.16215.1.16.2.24.2.5
		powerMode OBJECT-TYPE
			SYNTAX TypePowerMode
			MAX-ACCESS read-write
			STATUS current
			DESCRIPTION
				"Power Mode
				0 - Chip Run
				1 - full power down
				2 - standby
				3 - reset
				InDB = NO
				ELBIT_PERM(0x0000001F)
				ADMIN_PERM(0x00000000)
				TECH_PERM(0x000000000)
				USER_PERM(0x00000000)"
			::= { a2DPowerDownRegister 5 }

		
		-- 1.3.6.1.4.1.16215.1.16.2.24.3
		clckDistributur OBJECT IDENTIFIER ::= { afeandMacControl 3 }

		
		-- 1.3.6.1.4.1.16215.1.16.2.24.3.1
		enableA2dClk OBJECT-TYPE
			SYNTAX TypeDisableEnable
			MAX-ACCESS read-write
			STATUS current
			DESCRIPTION
				"Enable A2D clock
				0 - DisAble Clock
				1 - Enable  Clock
				InDB = NO
				ELBIT_PERM(0x0000001F)
				ADMIN_PERM(0x00000000)
				TECH_PERM(0x000000000)
				USER_PERM(0x00000000)"
			::= { clckDistributur 1 }

		
		-- 1.3.6.1.4.1.16215.1.16.2.24.3.2
		enableSpareRFClk OBJECT-TYPE
			SYNTAX TypeDisableEnable
			MAX-ACCESS read-write
			STATUS current
			DESCRIPTION
				"Enable Spare RF clock
				0 - DisAble Clock
				1 - Enable  Clock
				InDB = NO
				ELBIT_PERM(0x0000001F)
				ADMIN_PERM(0x00000000)
				TECH_PERM(0x000000000)
				USER_PERM(0x00000000)"
			::= { clckDistributur 2 }

		
		-- 1.3.6.1.4.1.16215.1.16.2.24.3.3
		enableTestClock OBJECT-TYPE
			SYNTAX TypeDisableEnable
			MAX-ACCESS read-write
			STATUS current
			DESCRIPTION
				"Enable Test clock
				0 - DisAble Clock
				1 - Enable  Clock
				InDB = NO
				ELBIT_PERM(0x0000001F)
				ADMIN_PERM(0x00000000)
				TECH_PERM(0x000000000)
				USER_PERM(0x00000000)"
			::= { clckDistributur 3 }

		
		-- 1.3.6.1.4.1.16215.1.16.2.24.3.4
		enableD2AClk OBJECT-TYPE
			SYNTAX TypeDisableEnable
			MAX-ACCESS read-write
			STATUS current
			DESCRIPTION
				"Enable D2A clock
				0 - DisAble Clock
				1 - Enable  Clock
				InDB = NO
				ELBIT_PERM(0x0000001F)
				ADMIN_PERM(0x00000000)
				TECH_PERM(0x000000000)
				USER_PERM(0x00000000)"
			::= { clckDistributur 4 }

		
		-- 1.3.6.1.4.1.16215.1.16.2.24.3.5
		rfSyntClockPower OBJECT-TYPE
			SYNTAX TypeRfSyntClkPower
			MAX-ACCESS read-write
			STATUS current
			DESCRIPTION
				"RF Synth clock Power
				0 - Disable RF Synt Clk
				1 - -9Dbm
				2 - -6Dbm
				3 - -3Dbm
				4 -  0Dbm
				7 -  7Dbm
				InDB = NO
				ELBIT_PERM(0x0000001F)
				ADMIN_PERM(0x00000000)
				TECH_PERM(0x000000000)
				USER_PERM(0x00000000)"
			::= { clckDistributur 5 }

		
		-- 1.3.6.1.4.1.16215.1.16.2.24.4
		ocxoFreqManual OBJECT-TYPE
			SYNTAX Integer32 (0..65535)
			MAX-ACCESS read-write
			STATUS current
			DESCRIPTION
				"OCXO Manual Frequency
				DEFVAL { 32767}
				InDB = YES
				TypeInDB=WORD
				ELBIT_PERM(0x000000FF)
				ADMIN_PERM(0x000000FF)
				TECH_PERM(0x000000FF)
				USER_PERM(0x000000FF)
				ELBIT_PERM(0xFFFFFF)
				ADMIN_PERM(0x00000000)
				TECH_PERM(0x000000000)
				USER_PERM(0x00000000)"
			::= { afeandMacControl 4 }

		
		-- 1.3.6.1.4.1.16215.1.16.2.24.5
		iduTxDCAatt OBJECT-TYPE
			SYNTAX TypeDCAAtt
			MAX-ACCESS read-write
			STATUS current
			DESCRIPTION
				"IDU TX DCA Att
				InDB = NO
				ELBIT_PERM(0xFFFFFF)
				ADMIN_PERM(0x00000000)
				TECH_PERM(0x000000000)
				USER_PERM(0x00000000)"
			::= { afeandMacControl 5 }

		
		-- 1.3.6.1.4.1.16215.1.16.2.24.6
		rxDCAatt OBJECT-TYPE
			SYNTAX TypeDCAAtt
			MAX-ACCESS read-write
			STATUS current
			DESCRIPTION
				"RX DCA Att
				InDB = NO
				ELBIT_PERM(0xFFFFFF)
				ADMIN_PERM(0x00000000)
				TECH_PERM(0x000000000)
				USER_PERM(0x00000000)"
			::= { afeandMacControl 6 }

		
		-- 1.3.6.1.4.1.16215.1.16.2.24.7
		ifConfigRegister OBJECT IDENTIFIER ::= { afeandMacControl 7 }

		
		-- 1.3.6.1.4.1.16215.1.16.2.24.7.1
		hw300MhzLoop OBJECT-TYPE
			SYNTAX TypeLoopSet
			MAX-ACCESS read-write
			STATUS current
			DESCRIPTION
				"HW Loop Hw on 300Mhz
				InDB = NO
				ELBIT_PERM(0xFFFFFF)
				ADMIN_PERM(0x00000000)
				TECH_PERM(0x000000000)
				USER_PERM(0x00000000)"
			::= { ifConfigRegister 1 }

		
		-- 1.3.6.1.4.1.16215.1.16.2.24.7.2
		hw140MhzLoop OBJECT-TYPE
			SYNTAX TypeLoopSet
			MAX-ACCESS read-write
			STATUS current
			DESCRIPTION
				"HW Loop Hw on 140Mhz
				InDB = NO
				ELBIT_PERM(0xFFFFFF)
				ADMIN_PERM(0x00000000)
				TECH_PERM(0x000000000)
				USER_PERM(0x00000000)"
			::= { ifConfigRegister 2 }

		
		-- 1.3.6.1.4.1.16215.1.16.2.24.7.3
		fixAttPath OBJECT-TYPE
			SYNTAX TypePathMode
			MAX-ACCESS read-write
			STATUS current
			DESCRIPTION
				"Path Att Path Mode
				InDB = NO
				ELBIT_PERM(0xFFFFFF)
				ADMIN_PERM(0x00000000)
				TECH_PERM(0x000000000)
				USER_PERM(0x00000000)"
			::= { ifConfigRegister 3 }

		
		-- 1.3.6.1.4.1.16215.1.16.2.24.8
		dac3484GeneralConfig OBJECT IDENTIFIER ::= { afeandMacControl 8 }

		
		-- 1.3.6.1.4.1.16215.1.16.2.24.8.1
		mixerGain OBJECT-TYPE
			SYNTAX TypeMixerGain
			MAX-ACCESS read-write
			STATUS current
			DESCRIPTION
				"Mixer Gain
				InDB = NO
				ELBIT_PERM(0xFFFFFF)
				ADMIN_PERM(0x00000000)
				TECH_PERM(0x000000000)
				USER_PERM(0x00000000)"
			::= { dac3484GeneralConfig 1 }

		
		-- 1.3.6.1.4.1.16215.1.16.2.24.8.2
		coarseDac OBJECT-TYPE
			SYNTAX TypeCoarseDAC
			MAX-ACCESS read-write
			STATUS current
			DESCRIPTION
				"Coarse DAC
				InDB = NO
				ELBIT_PERM(0xFFFFFF)
				ADMIN_PERM(0x00000000)
				TECH_PERM(0x000000000)
				USER_PERM(0x00000000)"
			::= { dac3484GeneralConfig 2 }

		
		-- 1.3.6.1.4.1.16215.1.16.2.24.8.3
		dacCWorks OBJECT-TYPE
			SYNTAX TypeDacWork
			MAX-ACCESS read-write
			STATUS current
			DESCRIPTION
				"Coarse DAC
				InDB = NO
				ELBIT_PERM(0xFFFFFF)
				ADMIN_PERM(0x00000000)
				TECH_PERM(0x000000000)
				USER_PERM(0x00000000)"
			::= { dac3484GeneralConfig 3 }

		
		-- 1.3.6.1.4.1.16215.1.16.2.24.8.4
		dacAWorks OBJECT-TYPE
			SYNTAX TypeDacWork
			MAX-ACCESS read-write
			STATUS current
			DESCRIPTION
				"InDB = NO
				ELBIT_PERM(0xFFFFFF)
				ADMIN_PERM(0x00000000)
				TECH_PERM(0x000000000)
				USER_PERM(0x00000000)"
			::= { dac3484GeneralConfig 4 }

		
		-- 1.3.6.1.4.1.16215.1.16.2.24.9
		dac3484SyncConfig OBJECT IDENTIFIER ::= { afeandMacControl 9 }

		
		-- 1.3.6.1.4.1.16215.1.16.2.24.9.1
		fifoIn OBJECT-TYPE
			SYNTAX TypeFifoInValue
			MAX-ACCESS read-write
			STATUS current
			DESCRIPTION
				"InDB = NO
				Can Get Value 0 to 3 or 8 - 11 other values are Ileagal
				ELBIT_PERM(0xFFFFFF)
				ADMIN_PERM(0x00000000)
				TECH_PERM(0x000000000)
				USER_PERM(0x00000000)"
			::= { dac3484SyncConfig 1 }

		
		-- 1.3.6.1.4.1.16215.1.16.2.24.9.2
		fifoOut OBJECT-TYPE
			SYNTAX TypeFifoValue
			MAX-ACCESS read-write
			STATUS current
			DESCRIPTION
				"InDB = NO
				ELBIT_PERM(0xFFFFFF)
				ADMIN_PERM(0x00000000)
				TECH_PERM(0x000000000)
				USER_PERM(0x00000000)"
			::= { dac3484SyncConfig 2 }

		
		-- 1.3.6.1.4.1.16215.1.16.2.24.9.3
		dataFormator OBJECT-TYPE
			SYNTAX TypeDataFormator
			MAX-ACCESS read-write
			STATUS current
			DESCRIPTION
				"InDB = NO
				ELBIT_PERM(0xFFFFFF)
				ADMIN_PERM(0x00000000)
				TECH_PERM(0x000000000)
				USER_PERM(0x00000000)"
			::= { dac3484SyncConfig 3 }

		
		-- 1.3.6.1.4.1.16215.1.16.2.24.9.4
		ncoAccumulator OBJECT-TYPE
			SYNTAX Integer32 (0..15)
			MAX-ACCESS read-write
			STATUS current
			DESCRIPTION
				"InDB = NO
				ELBIT_PERM(0xFFFFFF)
				ADMIN_PERM(0x00000000)
				TECH_PERM(0x000000000)
				USER_PERM(0x00000000)"
			::= { dac3484SyncConfig 4 }

		
		-- 1.3.6.1.4.1.16215.1.16.2.24.9.5
		clockDividerEn OBJECT-TYPE
			SYNTAX TypeDisableEnable
			MAX-ACCESS read-write
			STATUS current
			DESCRIPTION
				"InDB = NO
				ELBIT_PERM(0xFFFFFF)
				ADMIN_PERM(0x00000000)
				TECH_PERM(0x000000000)
				USER_PERM(0x00000000)"
			::= { dac3484SyncConfig 5 }

		
		-- 1.3.6.1.4.1.16215.1.16.2.24.9.6
		clockDividerSel OBJECT-TYPE
			SYNTAX TypeDivderSelect
			MAX-ACCESS read-write
			STATUS current
			DESCRIPTION
				"InDB = NO
				ELBIT_PERM(0xFFFFFF)
				ADMIN_PERM(0x00000000)
				TECH_PERM(0x000000000)
				USER_PERM(0x00000000)"
			::= { dac3484SyncConfig 6 }

		
		-- 1.3.6.1.4.1.16215.1.16.2.24.9.7
		mixerAB OBJECT-TYPE
			SYNTAX Integer32 (0..15)
			MAX-ACCESS read-write
			STATUS current
			DESCRIPTION
				"InDB = NO
				ELBIT_PERM(0xFFFFFF)
				ADMIN_PERM(0x00000000)
				TECH_PERM(0x000000000)
				USER_PERM(0x00000000)"
			::= { dac3484SyncConfig 7 }

		
		-- 1.3.6.1.4.1.16215.1.16.2.24.9.8
		mixerCD OBJECT-TYPE
			SYNTAX Integer32 (0..15)
			MAX-ACCESS read-write
			STATUS current
			DESCRIPTION
				"InDB = NO
				ELBIT_PERM(0xFFFFFF)
				ADMIN_PERM(0x00000000)
				TECH_PERM(0x000000000)
				USER_PERM(0x00000000)"
			::= { dac3484SyncConfig 8 }

		
		-- 1.3.6.1.4.1.16215.1.16.2.24.10
		dac3484NcoABFreq OBJECT-TYPE
			SYNTAX Integer32
			MAX-ACCESS read-write
			STATUS current
			DESCRIPTION
				"InDB = NO
				ELBIT_PERM(0xFFFFFF)
				ADMIN_PERM(0x00000000)
				TECH_PERM(0x000000000)
				USER_PERM(0x00000000)"
			::= { afeandMacControl 10 }

		
		-- 1.3.6.1.4.1.16215.1.16.2.24.11
		dac3484NcoCDFreq OBJECT-TYPE
			SYNTAX Integer32
			MAX-ACCESS read-write
			STATUS current
			DESCRIPTION
				"InDB = NO
				ELBIT_PERM(0xFFFFFF)
				ADMIN_PERM(0x00000000)
				TECH_PERM(0x000000000)
				USER_PERM(0x00000000)"
			::= { afeandMacControl 11 }

		
		-- 1.3.6.1.4.1.16215.1.16.2.24.12
		dac3484PllDivdersConfig OBJECT IDENTIFIER ::= { afeandMacControl 12 }

		
		-- 1.3.6.1.4.1.16215.1.16.2.24.12.1
		pll1Mdiv OBJECT-TYPE
			SYNTAX Integer32 (4..127)
			MAX-ACCESS read-write
			STATUS current
			DESCRIPTION
				"InDB = NO
				ELBIT_PERM(0xFFFFFF)
				ADMIN_PERM(0x00000000)
				TECH_PERM(0x000000000)
				USER_PERM(0x00000000)"
			::= { dac3484PllDivdersConfig 1 }

		
		-- 1.3.6.1.4.1.16215.1.16.2.24.12.2
		pll1Ndiv OBJECT-TYPE
			SYNTAX Integer32 (1..16)
			MAX-ACCESS read-write
			STATUS current
			DESCRIPTION
				"InDB = NO
				ELBIT_PERM(0xFFFFFF)
				ADMIN_PERM(0x00000000)
				TECH_PERM(0x000000000)
				USER_PERM(0x00000000)"
			::= { dac3484PllDivdersConfig 2 }

		
		-- 1.3.6.1.4.1.16215.1.16.2.24.12.3
		pll1Prescalar OBJECT-TYPE
			SYNTAX Integer32 (2..8)
			MAX-ACCESS read-write
			STATUS current
			DESCRIPTION
				"InDB = NO
				ELBIT_PERM(0xFFFFFF)
				ADMIN_PERM(0x00000000)
				TECH_PERM(0x000000000)
				USER_PERM(0x00000000)"
			::= { dac3484PllDivdersConfig 3 }

		
		-- 1.3.6.1.4.1.16215.1.16.2.24.12.4
		pll1VCOCoarse OBJECT-TYPE
			SYNTAX Integer32 (4..64)
			MAX-ACCESS read-write
			STATUS current
			DESCRIPTION
				"InDB = NO
				ELBIT_PERM(0xFFFFFF)
				ADMIN_PERM(0x00000000)
				TECH_PERM(0x000000000)
				USER_PERM(0x00000000)"
			::= { dac3484PllDivdersConfig 4 }

		
		-- 1.3.6.1.4.1.16215.1.16.2.24.13
		dac3484Pll4GeneralConfig OBJECT IDENTIFIER ::= { afeandMacControl 13 }

		
		-- 1.3.6.1.4.1.16215.1.16.2.24.13.1
		chargePump OBJECT-TYPE
			SYNTAX TypeChargePump
			MAX-ACCESS read-write
			STATUS current
			DESCRIPTION
				"InDB = NO
				ELBIT_PERM(0xFFFFFF)
				ADMIN_PERM(0x00000000)
				TECH_PERM(0x000000000)
				USER_PERM(0x00000000)"
			::= { dac3484Pll4GeneralConfig 1 }

		
		-- 1.3.6.1.4.1.16215.1.16.2.24.13.2
		vcoBiasTune OBJECT-TYPE
			SYNTAX Integer32 (0..3)
			MAX-ACCESS read-write
			STATUS current
			DESCRIPTION
				"InDB = NO
				ELBIT_PERM(0xFFFFFF)
				ADMIN_PERM(0x00000000)
				TECH_PERM(0x000000000)
				USER_PERM(0x00000000)"
			::= { dac3484Pll4GeneralConfig 2 }

		
		-- 1.3.6.1.4.1.16215.1.16.2.25
		alcApcControl OBJECT IDENTIFIER ::= { odu 25 }

		
		-- 1.3.6.1.4.1.16215.1.16.2.25.1
		powerAmplifierOnOFF OBJECT-TYPE
			SYNTAX TypePowerAmpONOFF
			MAX-ACCESS read-write
			STATUS current
			DESCRIPTION
				"Power Amplifier ON/OFF
				DEFVAL { 0x0 }
				InDB = NO
				TypeInDB=UCHAR
				ELBIT_PERM(0x0000FFFF)
				ADMIN_PERM(0x0000FFFF)
				TECH_PERM(0x0000FFFF)
				USER_PERM(0x0000FFFF)."
			::= { alcApcControl 1 }

		
		-- 1.3.6.1.4.1.16215.1.16.2.25.2
		powerSupply10VEnable OBJECT-TYPE
			SYNTAX TypePs10vOnOFF
			MAX-ACCESS read-write
			STATUS current
			DESCRIPTION
				"Ps 10v Enable disable
				DEFVAL { 0x0 }
				InDB = NO
				TypeInDB=UCHAR
				ELBIT_PERM(0x0000FFFF)
				ADMIN_PERM(0x0000FFFF)
				TECH_PERM(0x0000FFFF)
				USER_PERM(0x0000FFFF)."
			::= { alcApcControl 2 }

		
		-- 1.3.6.1.4.1.16215.1.16.2.25.3
		manualModeSelect OBJECT-TYPE
			SYNTAX TypeManualMode
			MAX-ACCESS read-write
			STATUS current
			DESCRIPTION
				"Manual Mode Select 0 - AutoMode 1 -VVA/DCA select Manualy in AGC control register
				DEFVAL { 0x0 }
				InDB = NO
				TypeInDB=UCHAR
				ELBIT_PERM(0x0000FFFF)
				ADMIN_PERM(0x0000FFFF)
				TECH_PERM(0x0000FFFF)
				USER_PERM(0x0000FFFF)."
			::= { alcApcControl 3 }

		
		-- 1.3.6.1.4.1.16215.1.16.2.25.4
		currentTempRange OBJECT-TYPE
			SYNTAX Integer32 (0..3)
			MAX-ACCESS read-write
			STATUS current
			DESCRIPTION
				"Select Temperture Range
				DEFVAL { 0x0 }
				InDB = NO
				TypeInDB=UCHAR
				ELBIT_PERM(0x0000FFFF)
				ADMIN_PERM(0x0000FFFF)
				TECH_PERM(0x0000FFFF)
				USER_PERM(0x0000FFFF)."
			::= { alcApcControl 4 }

		
		-- 1.3.6.1.4.1.16215.1.16.2.25.5
		apcModeSelect OBJECT-TYPE
			SYNTAX TypeApcMode
			MAX-ACCESS read-write
			STATUS current
			DESCRIPTION
				"Apc mode Select
				DIsable mean No APC Enable means works with APC
				DEFVAL { 0x0 }
				InDB = NO
				TypeInDB=UCHAR
				ELBIT_PERM(0x0000FFFF)
				ADMIN_PERM(0x0000FFFF)
				TECH_PERM(0x0000FFFF)
				USER_PERM(0x0000FFFF)."
			::= { alcApcControl 5 }

		
		-- 1.3.6.1.4.1.16215.1.16.2.25.6
		alcManulaVVA1Value OBJECT-TYPE
			SYNTAX TypeVVAValue
			MAX-ACCESS read-write
			STATUS current
			DESCRIPTION
				"Select selecet ALC VVA1 Manual
				DEFVAL { 0x0 }
				InDB = NO
				TypeInDB=UCHAR
				ELBIT_PERM(0x0000FFFF)
				ADMIN_PERM(0x0000FFFF)
				TECH_PERM(0x0000FFFF)
				USER_PERM(0x0000FFFF)."
			::= { alcApcControl 6 }

		
		-- 1.3.6.1.4.1.16215.1.16.2.25.7
		alcManulaVVA2Value OBJECT-TYPE
			SYNTAX TypeVVAValue
			MAX-ACCESS read-write
			STATUS current
			DESCRIPTION
				"Select selecet ALC VVA2 Manual
				DEFVAL { 0x0 }
				InDB = NO
				TypeInDB=UCHAR
				ELBIT_PERM(0x0000FFFF)
				ADMIN_PERM(0x0000FFFF)
				TECH_PERM(0x0000FFFF)
				USER_PERM(0x0000FFFF)."
			::= { alcApcControl 7 }

		
		-- 1.3.6.1.4.1.16215.1.16.2.25.8
		alcManulaDCAValue OBJECT-TYPE
			SYNTAX TypeDCAValue
			MAX-ACCESS read-write
			STATUS current
			DESCRIPTION
				"Select selecet ALC DCA Manual
				DEFVAL { 0x0 }
				InDB = NO
				TypeInDB=UCHAR
				ELBIT_PERM(0x0000FFFF)
				ADMIN_PERM(0x0000FFFF)
				TECH_PERM(0x0000FFFF)
				USER_PERM(0x0000FFFF)."
			::= { alcApcControl 8 }

		
		-- 1.3.6.1.4.1.16215.1.16.2.25.9
		alcManualLevel OBJECT-TYPE
			SYNTAX Integer32 (-12..38)
			MAX-ACCESS read-write
			STATUS current
			DESCRIPTION
				"Select selecet ALC Desire Level
				DEFVAL { 0x0 }
				InDB = NO
				TypeInDB=UCHAR
				ELBIT_PERM(0x0000FFFF)
				ADMIN_PERM(0x0000FFFF)
				TECH_PERM(0x0000FFFF)
				USER_PERM(0x0000FFFF)."
			::= { alcApcControl 9 }

		
		-- 1.3.6.1.4.1.16215.1.16.2.25.10
		alcChangeThershold OBJECT-TYPE
			SYNTAX Integer32 (0..255)
			MAX-ACCESS read-write
			STATUS current
			DESCRIPTION
				"Select selecet ALC Change Thershold
				DEFVAL { 0x0 }
				InDB = NO
				TypeInDB=UCHAR
				ELBIT_PERM(0x0000FFFF)
				ADMIN_PERM(0x0000FFFF)
				TECH_PERM(0x0000FFFF)
				USER_PERM(0x0000FFFF)."
			::= { alcApcControl 10 }

		
		-- 1.3.6.1.4.1.16215.1.16.2.25.11
		desiredRFRssi OBJECT-TYPE
			SYNTAX Integer32 (0..255)
			MAX-ACCESS read-write
			STATUS current
			DESCRIPTION
				"Desired RF RSSI
				DEFVAL { 0x0 }
				InDB = NO
				TypeInDB=UCHAR
				ELBIT_PERM(0x0000FFFF)
				ADMIN_PERM(0x0000FFFF)
				TECH_PERM(0x0000FFFF)
				USER_PERM(0x0000FFFF)."
			::= { alcApcControl 11 }

		
		-- 1.3.6.1.4.1.16215.1.16.2.25.12
		desiredIFRssi OBJECT-TYPE
			SYNTAX Integer32 (0..255)
			MAX-ACCESS read-write
			STATUS current
			DESCRIPTION
				"Desired IF RSSI
				DEFVAL { 0x0 }
				InDB = NO
				TypeInDB=UCHAR
				ELBIT_PERM(0x0000FFFF)
				ADMIN_PERM(0x0000FFFF)
				TECH_PERM(0x0000FFFF)
				USER_PERM(0x0000FFFF)."
			::= { alcApcControl 12 }

		
		-- 1.3.6.1.4.1.16215.1.16.2.25.13
		rssiRefernceValue OBJECT-TYPE
			SYNTAX Integer32 (0..255)
			MAX-ACCESS read-write
			STATUS current
			DESCRIPTION
				"Rssi Refernce Value to decrease value that 
				we read from FPGA
				DEFVAL { 220 }
				InDB = YES
				TypeInDB=UCHAR
				ELBIT_PERM(0x0000FFFF)
				ADMIN_PERM(0x0000FFFF)
				TECH_PERM(0x0000FFFF)
				USER_PERM(0x0000FFFF)."
			::= { alcApcControl 13 }

		
		-- 1.3.6.1.4.1.16215.1.16.2.25.14
		resetFpga OBJECT-TYPE
			SYNTAX TypeOnOff
			MAX-ACCESS read-write
			STATUS current
			DESCRIPTION
				"Reset FPGA devce
				DEFVAL { 1 }
				InDB = NO
				TypeInDB=UCHAR
				ELBIT_PERM(0x000000FF)
				ADMIN_PERM(0x00000000)
				TECH_PERM(0x000000000)
				USER_PERM(0x000000000)"
			::= { alcApcControl 14 }

		
		-- 1.3.6.1.4.1.16215.1.16.2.25.15
		agcDesiredLevel OBJECT-TYPE
			SYNTAX TypeAgcDesiredLevel
			MAX-ACCESS read-write
			STATUS current
			DESCRIPTION
				"AGC desired level
				DEFVAL{120}
				InDB = YES
				TypeInDB=UCHAR
				ELBIT_PERM(0xFFFFFFFF)
				ADMIN_PERM(0xFFFFFFFF)
				TECH_PERM(0xFFFFFFFF)
				USER_PERM(0xFFFFFFFF)"
			::= { alcApcControl 15 }

		
		-- 1.3.6.1.4.1.16215.1.16.2.25.16
		ifAGCConvergenceWindow OBJECT-TYPE
			SYNTAX Integer32 (0..255)
			MAX-ACCESS read-write
			STATUS current
			DESCRIPTION
				"if AGC Convergence Window
				DEFVAL{1}
				InDB = YES
				TypeInDB=UCHAR
				ELBIT_PERM(0xFFFFFFFF)
				ADMIN_PERM(0xFFFFFFFF)
				TECH_PERM(0xFFFFFFFF)
				USER_PERM(0xFFFFFFFF)"
			::= { alcApcControl 16 }

			   
		-- 1.3.6.1.4.1.16215.1.16.2.25.17
		agcGainDb OBJECT-TYPE
			SYNTAX Integer32 (0..255)
			MAX-ACCESS read-only
			STATUS current
			DESCRIPTION
				"AGC Gain DB
				DEFVAL { 0x0 }
				InDB = NO
				TypeInDB=UCHAR
				ELBIT_PERM(0x0000FFFF)
				ADMIN_PERM(0x0000FFFF)
				TECH_PERM(0x0000FFFF)
				USER_PERM(0x0000FFFF)."
			::= { alcApcControl 17 }

		frequencyHopNumber OBJECT-TYPE
			SYNTAX TypeFrequencyHopNumber
			MAX-ACCESS read-write
			STATUS current
			DESCRIPTION
				"This Value is write automaticaly to 
				 address 0x100011c8 and addres 0x100019c8
				DEFVAL{0}
				InDB = NO
				TypeInDB=UCHAR
				ELBIT_PERM(0xFFFFFFFF)
				ADMIN_PERM(0xFFFFFFFF)
				TECH_PERM(0xFFFFFFFF)
				USER_PERM(0xFFFFFFFF)"
			::= { alcApcControl 18 } 
			
			
						
		powerControlMode OBJECT-TYPE
			SYNTAX TypeTxLevel
			MAX-ACCESS read-write
			STATUS current
			DESCRIPTION
				"Tx Level
				DEFVAL { 1}
				InDB = YES
				TypeInDB=UCHAR
				ELBIT_PERM(0x00000006)
				ADMIN_PERM(0x00000006)
				TECH_PERM(0x00000006)
				USER_PERM(0x00000006)"
			::= { alcApcControl 19 }
		
		-- 1.3.6.1.4.1.16215.1.16.2.26
		modemlockNotification NOTIFICATION-TYPE
			OBJECTS { oduModem1ModemLock, oduModem2ModemLock }
			STATUS current
			DESCRIPTION 
				"Send Notification to manager
				InDB = NO
				TypeInDB=UCHAR
				ELBIT_PERM(0x0000FFFF)
				ADMIN_PERM(0x0000FFFF)
				TECH_PERM(0x0000FFFF)
				USER_PERM(0x0000FFFF)."
			::= { odu 26 }
			  
			  
-- 1.3.6.1.4.1.16215.1.16.2.27
		topologyConfiguration OBJECT IDENTIFIER ::={odu 27}
				-- 1.3.6.1.4.1.16215.1.16.2.27.2
				link1    OBJECT IDENTIFIER ::={topologyConfiguration 2}   
				           
				    -- 1.3.6.1.4.1.16215.1.16.2.27.2.1
					rxLink1 OBJECT IDENTIFIER ::={link1 1} 
					     -- 1.3.6.1.4.1.16215.1.16.2.27.1.2.1
					   	link1RxWorkingMOde OBJECT-TYPE
						SYNTAX Integer32(0..16) 
						MAX-ACCESS read-write
						STATUS current
						DESCRIPTION
						"WorkingMode"
						::= { rxLink1 1 } 
						
				     -- 1.3.6.1.4.1.16215.1.16.2.27.1.2.2
					   	link1RxHARQ  OBJECT-TYPE
						SYNTAX Integer32(0..1) 
						MAX-ACCESS read-write
						STATUS current
						DESCRIPTION
						"0 OFF
						1 ON"
						::= { rxLink1 2 }
						
				     -- 1.3.6.1.4.1.16215.1.16.2.27.1.2.3
					   	link1RxLinkEnable  OBJECT-TYPE
						SYNTAX Integer32(0..1) 
						MAX-ACCESS read-write
						STATUS current
						DESCRIPTION
						"0 - not available
						1- available"
						::= { rxLink1 3 }
												
				     -- 1.3.6.1.4.1.16215.1.16.2.27.1.2.4
					   	link1RxACMState  OBJECT-TYPE
						SYNTAX Integer32(0..1) 
						MAX-ACCESS read-write
						STATUS current
						DESCRIPTION
						"0 OFF
						1 ON"
						::= { rxLink1 4 }
						
						-- 1.3.6.1.4.1.16215.1.16.2.27.1.2.5
						link1RxCarrierBitmap OBJECT-TYPE
						SYNTAX Integer32(1..63) 
						MAX-ACCESS read-write
						STATUS current
						DESCRIPTION
						"interger 1-63 : 6 bits bitmap"
						::= { rxLink1 5 }					
					
					  -- 1.3.6.1.4.1.16215.1.16.2.27.2.2
					txLink1	 OBJECT IDENTIFIER ::={link1 2}
					  -- 1.3.6.1.4.1.16215.1.16.2.27.2.2.1
					   	link1TxWorkingMOde OBJECT-TYPE
						SYNTAX Integer32(0..16) 
						MAX-ACCESS read-write
						STATUS current
						DESCRIPTION
						"WorkingMode"
						::= { txLink1 1 } 
						
				     -- 1.3.6.1.4.1.16215.1.16.2.27.2.2.2
					    link1TxHARQ  OBJECT-TYPE
						SYNTAX Integer32(0..1) 
						MAX-ACCESS read-write
						STATUS current
						DESCRIPTION
						"0 OFF
						1 ON"
						::= { txLink1 2 }
						
				     -- 1.3.6.1.4.1.16215.1.16.2.27.2.2.3
					   	link1TxLinkEnable  OBJECT-TYPE
						SYNTAX Integer32(0..1) 
						MAX-ACCESS read-write
						STATUS current
						DESCRIPTION
						"0 - not available
						1- available"
						::= { txLink1 3 }
												
				     -- 1.3.6.1.4.1.16215.1.16.2.27.2.2.4
					   	link1TxACMState  OBJECT-TYPE
						SYNTAX Integer32(0..1) 
						MAX-ACCESS read-write
						STATUS current
						DESCRIPTION
						"0 OFF
						1 ON"
						::= { txLink1 4 }
						
						-- 1.3.6.1.4.1.16215.1.16.2.27.2.2.5
						link1TxCarrierBitmap OBJECT-TYPE
						SYNTAX Integer32(1..63) 
						MAX-ACCESS read-write
						STATUS current
						DESCRIPTION
						"interger 1-63 : 6 bits bitmap"
						::= { txLink1 5 }
   							
												
						-- 1.3.6.1.4.1.16215.1.16.2.27.2.3
						link1PairedStationID OBJECT-TYPE
						SYNTAX Integer32(0..4095) 
						MAX-ACCESS read-write
						STATUS current
						DESCRIPTION
						"pairedStationId"
						::= { link1 3 }					 

						-- 1.3.6.1.4.1.16215.1.16.2.27.2.4
						link1GoodToGo OBJECT-TYPE
						SYNTAX Integer32 (0..1) 
						MAX-ACCESS read-write
						STATUS current
						DESCRIPTION
						"0 - Invalid parameters
						1- Valid Parameters "
						::= { link1 4 }

		
				-- 1.3.6.1.4.1.16215.1.16.2.27.3
				link2    OBJECT IDENTIFIER ::={topologyConfiguration 3}  
			            				    -- 1.3.6.1.4.1.16215.1.16.2.27.2.1
					rxLink2 OBJECT IDENTIFIER ::={link2 1} 
					     -- 1.3.6.1.4.1.16215.1.16.2.27.1.2.1
					   	link2RxWorkingMOde OBJECT-TYPE
						SYNTAX Integer32(0..16) 
						MAX-ACCESS read-write
						STATUS current
						DESCRIPTION
						"WorkingMode"
						::= { rxLink2 1 } 
						
				     -- 1.3.6.1.4.1.16215.1.16.2.27.1.2.2
					   	link2RxHARQ  OBJECT-TYPE
						SYNTAX Integer32(0..1) 
						MAX-ACCESS read-write
						STATUS current
						DESCRIPTION
						"0 OFF
						1 ON"
						::= { rxLink2 2 }
						
				     -- 1.3.6.1.4.1.16215.1.16.2.27.1.2.3
					   	link2RxLinkEnable  OBJECT-TYPE
						SYNTAX Integer32(0..1) 
						MAX-ACCESS read-write
						STATUS current
						DESCRIPTION
						"0 - not available
						1- available"
						::= { rxLink2 3 }
												
				     -- 1.3.6.1.4.1.16215.1.16.2.27.1.2.4
					   	link2RxACMState  OBJECT-TYPE
						SYNTAX Integer32(0..1) 
						MAX-ACCESS read-write
						STATUS current
						DESCRIPTION
						"0 OFF
						1 ON"
						::= { rxLink2 4 }
						
						-- 1.3.6.1.4.1.16215.1.16.2.27.1.2.5
						link2RxCarrierBitmap OBJECT-TYPE
						SYNTAX Integer32(1..63) 
						MAX-ACCESS read-write
						STATUS current
						DESCRIPTION
						"interger 1-63 : 6 bits bitmap"
						::= { rxLink2 5 }					
					
					  -- 1.3.6.1.4.1.16215.1.16.2.27.2.2
					txLink2 OBJECT IDENTIFIER ::={link2 2}
					  -- 1.3.6.1.4.1.16215.1.16.2.27.2.2.1
					   	link2TxWorkingMOde OBJECT-TYPE
						SYNTAX Integer32(0..16) 
						MAX-ACCESS read-write
						STATUS current
						DESCRIPTION
						"WorkingMode"
						::= { txLink2 1 } 
						
				     -- 1.3.6.1.4.1.16215.1.16.2.27.2.2.2
					    link2TxHARQ  OBJECT-TYPE
						SYNTAX Integer32(0..1) 
						MAX-ACCESS read-write
						STATUS current
						DESCRIPTION
						"0 OFF
						1 ON"
						::= { txLink2 2 }
						
				     -- 1.3.6.1.4.1.16215.1.16.2.27.2.2.3
					   	link2TxLinkEnable  OBJECT-TYPE
						SYNTAX Integer32(0..1) 
						MAX-ACCESS read-write
						STATUS current
						DESCRIPTION
						"0 - not available
						1- available"
						::= { txLink2 3 }
												
				     -- 1.3.6.1.4.1.16215.1.16.2.27.2.2.4
					   	link2TxACMState  OBJECT-TYPE
						SYNTAX Integer32(0..1) 
						MAX-ACCESS read-write
						STATUS current
						DESCRIPTION
						"0 OFF
						1 ON"
						::= { txLink2 4 }
						
						-- 1.3.6.1.4.1.16215.1.16.2.27.2.2.5
						link2TxCarrierBitmap OBJECT-TYPE
						SYNTAX Integer32(1..63) 
						MAX-ACCESS read-write
						STATUS current
						DESCRIPTION
						"interger 1-63 : 6 bits bitmap"
						::= { txLink2 5 }
												
												
						-- 1.3.6.1.4.1.16215.1.16.2.27.3.3
						link2PairedStationID OBJECT-TYPE
						SYNTAX Integer32(0..4095) 
						MAX-ACCESS read-write
						STATUS current
						DESCRIPTION
						"pairedStationId"
						::= { link2 3 }					 

						-- 1.3.6.1.4.1.16215.1.16.2.27.3.4
						link2GoodToGo OBJECT-TYPE
						SYNTAX Integer32 (0..1) 
						MAX-ACCESS read-write
						STATUS current
						DESCRIPTION
						"0 - Invalid parameters
						1- Valid Parameters "
						::= { link2 4 }
                                             
                                             
                                         

				-- 1.3.6.1.4.1.16215.1.16.2.27.4
				link3    OBJECT IDENTIFIER ::={topologyConfiguration 4}
				      rxLink3 OBJECT IDENTIFIER ::={link3 1} 
					     -- 1.3.6.1.4.1.16215.1.16.2.27.1.2.1
					   	link3RxWorkingMOde OBJECT-TYPE
						SYNTAX Integer32(0..16) 
						MAX-ACCESS read-write
						STATUS current
						DESCRIPTION
						"WorkingMode"
						::= { rxLink3 1 } 
						
				     -- 1.3.6.1.4.1.16215.1.16.2.27.1.2.2
					   	link3RxHARQ  OBJECT-TYPE
						SYNTAX Integer32(0..1) 
						MAX-ACCESS read-write
						STATUS current
						DESCRIPTION
						"0 OFF
						1 ON"
						::= { rxLink3 2 }
						
				     -- 1.3.6.1.4.1.16215.1.16.2.27.1.2.3
					   	link3RxLinkEnable  OBJECT-TYPE
						SYNTAX Integer32(0..1) 
						MAX-ACCESS read-write
						STATUS current
						DESCRIPTION
						"0 - not available
						1- available"
						::= { rxLink3 3 }
												
				     -- 1.3.6.1.4.1.16215.1.16.2.27.1.2.4
					   	link3RxACMState  OBJECT-TYPE
						SYNTAX Integer32(0..1) 
						MAX-ACCESS read-write
						STATUS current
						DESCRIPTION
						"0 OFF
						1 ON"
						::= { rxLink3 4 }
						
						-- 1.3.6.1.4.1.16215.1.16.2.27.1.2.5
						link3RxCarrierBitmap OBJECT-TYPE
						SYNTAX Integer32(1..63) 
						MAX-ACCESS read-write
						STATUS current
						DESCRIPTION
						"interger 1-63 : 6 bits bitmap"
						::= { rxLink3 5 }					
					
					  -- 1.3.6.1.4.1.16215.1.16.2.27.2.2
					txLink3 OBJECT IDENTIFIER ::={link3 2}
					  -- 1.3.6.1.4.1.16215.1.16.2.27.2.2.1
					   	link3TxWorkingMOde OBJECT-TYPE
						SYNTAX Integer32(0..16) 
						MAX-ACCESS read-write
						STATUS current
						DESCRIPTION
						"WorkingMode"
						::= { txLink3 1 } 
						
				     -- 1.3.6.1.4.1.16215.1.16.2.27.2.2.2
					    link3TxHARQ  OBJECT-TYPE
						SYNTAX Integer32(0..1) 
						MAX-ACCESS read-write
						STATUS current
						DESCRIPTION
						"0 OFF
						1 ON"
						::= { txLink3 2 }
						
				     -- 1.3.6.1.4.1.16215.1.16.2.27.2.2.3
					   	link3TxLinkEnable  OBJECT-TYPE
						SYNTAX Integer32(0..1) 
						MAX-ACCESS read-write
						STATUS current
						DESCRIPTION
						"0 - not available
						1- available"
						::= { txLink3 3 }
												
				     -- 1.3.6.1.4.1.16215.1.16.2.27.2.2.4
					   	link3TxACMState  OBJECT-TYPE
						SYNTAX Integer32(0..1) 
						MAX-ACCESS read-write
						STATUS current
						DESCRIPTION
						"0 OFF
						1 ON"
						::= { txLink3 4 }
						
						-- 1.3.6.1.4.1.16215.1.16.2.27.2.2.5
						link3TxCarrierBitmap OBJECT-TYPE
						SYNTAX Integer32(1..63) 
						MAX-ACCESS read-write
						STATUS current
						DESCRIPTION
						"interger 1-63 : 6 bits bitmap"
						::= { txLink3 5 }
							
												
						-- 1.3.6.1.4.1.16215.1.16.2.27.4.3
						link3PairedStationID OBJECT-TYPE
						SYNTAX Integer32(0..4095) 
						MAX-ACCESS read-write
						STATUS current
						DESCRIPTION
						"pairedStationId"
						::= { link3 3 }			

						-- 1.3.6.1.4.1.16215.1.16.2.27.4.4
						link3GoodToGo OBJECT-TYPE
						SYNTAX Integer32 (0..1) 
						MAX-ACCESS read-write
						STATUS current
						DESCRIPTION
						"0 - Invalid parameters
						1- Valid Parameters "
						::= { link3 4 }
					
				-- 1.3.6.1.4.1.16215.1.16.2.27.5
				hopScheme OBJECT-TYPE
				SYNTAX TypeHopFreqTableSelect
				MAX-ACCESS read-write
				STATUS current
				DESCRIPTION
				"integer range to be chnaged"
				::= { topologyConfiguration 5 } 
						 
				-- 1.3.6.1.4.1.16215.1.16.2.27.6   
				makmashType OBJECT-TYPE
				SYNTAX Integer32 (0..1)
				MAX-ACCESS read-write
				STATUS current
				DESCRIPTION
				"0-su, 1-au"
				::= { topologyConfiguration 6 }
			
				-- 1.3.6.1.4.1.16215.1.16.2.27.7
				myStationId OBJECT-TYPE
				SYNTAX Integer32(0..4095)
				MAX-ACCESS read-write
				STATUS current
				DESCRIPTION
				"Integer"
				::= { topologyConfiguration 7 } 
				
				-- 1.3.6.1.4.1.16215.1.16.2.27.8				                                  
				rxBand OBJECT-TYPE
				SYNTAX TypeBandSelect 
				MAX-ACCESS read-write
				STATUS current
				DESCRIPTION
				"1-4 Filter"
				::= { topologyConfiguration 8 }      
				
				-- 1.3.6.1.4.1.16215.1.16.2.27.9				
				txBand OBJECT-TYPE
				SYNTAX TypeBandSelect 
				MAX-ACCESS read-write
				STATUS current
				DESCRIPTION
				"1-4 Filter"
				::= { topologyConfiguration 9 }	 
				
				-- 1.3.6.1.4.1.16215.1.16.2.27.10				
				rxSubBand OBJECT-TYPE
				SYNTAX Integer32 (0..1)
				MAX-ACCESS read-write
				STATUS current
				DESCRIPTION
				"0 - Left side
				1 - Right side"
				::= { topologyConfiguration 10 }
					
				-- 1.3.6.1.4.1.16215.1.16.2.27.11							
				txSubBand OBJECT-TYPE
				SYNTAX Integer32 (0..1)
				MAX-ACCESS read-write
				STATUS current
				DESCRIPTION
				"0 - Left side
				1 - Right side"
				::= { topologyConfiguration 11 } 
				
				-- 1.3.6.1.4.1.16215.1.16.2.27.12	
				rxFrequency OBJECT-TYPE
				SYNTAX TypeFrequencyConfiguration 
				MAX-ACCESS read-write
				STATUS current
				DESCRIPTION
				"frequency 1-4"
				::= { topologyConfiguration 12 }
				
				-- 1.3.6.1.4.1.16215.1.16.2.27.13				
				txFrequency OBJECT-TYPE
				SYNTAX TypeFrequencyConfiguration 
				MAX-ACCESS read-write
				STATUS current
				DESCRIPTION
				"frequency 1-4"
				::= { topologyConfiguration 13 }
			
				-- 1.3.6.1.4.1.16215.1.16.2.27.14					
				frequencyHopMode OBJECT-TYPE
				SYNTAX TypeFrequencyHopNumber
				MAX-ACCESS read-write
				STATUS current
				DESCRIPTION
					"Hop mode"
				::= { topologyConfiguration 14 }
	                           
				-- 1.3.6.1.4.1.16215.1.16.2.27.15                         
				publicGoodToGo OBJECT-TYPE
				SYNTAX Integer32 (0..1)
				MAX-ACCESS read-write
				STATUS current
				DESCRIPTION
				"0 - Invalid
				1 - Valid"
				::= { topologyConfiguration 15 } 
										            
				            			
-- 1.3.6.1.4.1.16215.1.16.2.28
		monitor OBJECT IDENTIFIER ::={odu 28}
				-- 1.3.6.1.4.1.16215.1.16.2.28.1
				link1Monitor OBJECT IDENTIFIER ::= { monitor 1 }
						
							-- 1.3.6.1.4.1.16215.1.16.2.28.1.1
							per1 OBJECT-TYPE
							SYNTAX Integer32 
							MAX-ACCESS read-only
							STATUS current
							DESCRIPTION
							"BadPacket/TotalHopCnt * 100 "
							::= { link1Monitor 1 }
							-- 1.3.6.1.4.1.16215.1.16.2.28.1.2
							sync1 OBJECT-TYPE
							SYNTAX Integer32 
							MAX-ACCESS read-only
							STATUS current
							DESCRIPTION
							"Marks\TotalHopCnt * 100"
							::= { link1Monitor 2 }							
							-- 1.3.6.1.4.1.16215.1.16.2.28.1.3
							rssi-max1 OBJECT-TYPE
							SYNTAX Integer32 
							MAX-ACCESS read-only
							STATUS current
							DESCRIPTION
							"from my partner Rssi"
							::= { link1Monitor 3 }	
							-- 1.3.6.1.4.1.16215.1.16.2.28.1.4
							rssi-min1 OBJECT-TYPE
							SYNTAX Integer32 
							MAX-ACCESS read-only
							STATUS current
							DESCRIPTION
							"from my partner Rssi"
							::= { link1Monitor 4 }
							-- 1.3.6.1.4.1.16215.1.16.2.28.1.5		
							islink1up OBJECT-TYPE
							SYNTAX Integer32 (0..1) 
							MAX-ACCESS read-only
							STATUS current
							DESCRIPTION
							"0	- link is down
							1	- link is up"
							::= { link1Monitor 5 }								
				-- 1.3.6.1.4.1.16215.1.16.2.28.2
				link2Monitor OBJECT IDENTIFIER ::= { monitor 2 }
						
							-- 1.3.6.1.4.1.16215.1.16.2.28.2.1
							per2 OBJECT-TYPE
							SYNTAX Integer32 
							MAX-ACCESS read-only
							STATUS current
							DESCRIPTION
							"BadPacket/TotalHopCnt * 100 "
							::= { link2Monitor 1 }
							-- 1.3.6.1.4.1.16215.1.16.2.28.2.2
							sync2 OBJECT-TYPE
							SYNTAX Integer32 
							MAX-ACCESS read-only
							STATUS current
							DESCRIPTION
							"Marks\TotalHopCnt * 100"
							::= { link2Monitor 2 }							
							-- 1.3.6.1.4.1.16215.1.16.2.28.2.3
							rssi-max2 OBJECT-TYPE
							SYNTAX Integer32 
							MAX-ACCESS read-only
							STATUS current
							DESCRIPTION
							"from my partner Rssi"
							::= { link2Monitor 3 }	
							-- 1.3.6.1.4.1.16215.1.16.2.28.2.4
							rssi-min2 OBJECT-TYPE
							SYNTAX Integer32 
							MAX-ACCESS read-only
							STATUS current
							DESCRIPTION
							"from my partner Rssi"
							::= { link2Monitor 4 }
							-- 1.3.6.1.4.1.16215.1.16.2.28.2.5
							islink2up OBJECT-TYPE
							SYNTAX Integer32 (0..1) 
							MAX-ACCESS read-only
							STATUS current
							DESCRIPTION
							"0	- link is down
							1	- link is up"
							::= { link2Monitor 5 }			
				-- 1.3.6.1.4.1.16215.1.16.2.28.3
				link3Monitor OBJECT IDENTIFIER ::= { monitor 3 }
						
							-- 1.3.6.1.4.1.16215.1.16.2.28.3.1
							per3 OBJECT-TYPE
							SYNTAX Integer32 
							MAX-ACCESS read-only
							STATUS current
							DESCRIPTION
							"BadPacket/TotalHopCnt * 100 "
							::= { link3Monitor 1 }
							-- 1.3.6.1.4.1.16215.1.16.2.28.3.2
							sync3 OBJECT-TYPE
							SYNTAX Integer32 
							MAX-ACCESS read-only
							STATUS current
							DESCRIPTION
							"Marks\TotalHopCnt * 100"
							::= { link3Monitor 2 }							
							-- 1.3.6.1.4.1.16215.1.16.2.28.3.3
							rssi-max3 OBJECT-TYPE
							SYNTAX Integer32 
							MAX-ACCESS read-only
							STATUS current
							DESCRIPTION
							"from my partner Rssi"
							::= { link3Monitor 3 }	
							-- 1.3.6.1.4.1.16215.1.16.2.28.3.4
							rssi-min3 OBJECT-TYPE
							SYNTAX Integer32 
							MAX-ACCESS read-only
							STATUS current
							DESCRIPTION
							"from my partner Rssi"
							::= { link3Monitor 4 }
							-- 1.3.6.1.4.1.16215.1.16.2.28.3.5
							islink3up OBJECT-TYPE
							SYNTAX Integer32 (0..1)
							MAX-ACCESS read-only
							STATUS current
							DESCRIPTION
							"0	- link is down
							1	- link is up"
							::= { link3Monitor 5 }	

		moduleAHud OBJECT IDENTIFIER ::={odu 29}
		
		spiClockRateSelect OBJECT-TYPE
			SYNTAX TypeSpiClockCntrol
			MAX-ACCESS read-write
			STATUS current
			DESCRIPTION
				"Select SPI Cleck Rate.
				DEFVAL { 1 }
				InDB = NO
				TypeInDB=UCHAR
				ELBIT_PERM(0x00000003)
				ADMIN_PERM(0x00000003)
				TECH_PERM(0x00000003)
				USER_PERM(0x00000003)"
			::= { moduleAHud 1 }

		pll1PowerEnable OBJECT-TYPE
			SYNTAX TypePllPowerEnable
			MAX-ACCESS read-write
			STATUS current
			DESCRIPTION
				"Select PLL power Enable.
				DEFVAL { 2 }
				InDB = NO
				TypeInDB=UCHAR
				ELBIT_PERM(0x00000003)
				ADMIN_PERM(0x00000003)
				TECH_PERM(0x00000003)
				USER_PERM(0x00000003)"
			::= { moduleAHud 2 }

		pll2PowerEnable OBJECT-TYPE
			SYNTAX TypePllPowerEnable
			MAX-ACCESS read-write
			STATUS current
			DESCRIPTION
				"Select PLL power Enable.
				DEFVAL { 2 }
				InDB = NO
				TypeInDB=UCHAR
				ELBIT_PERM(0x00000003)
				ADMIN_PERM(0x00000003)
				TECH_PERM(0x00000003)
				USER_PERM(0x00000003)"
			::= { moduleAHud 3 }

		pll3PowerEnable OBJECT-TYPE
			SYNTAX TypePllPowerEnable
			MAX-ACCESS read-write
			STATUS current
			DESCRIPTION
				"Select PLL power Enable.
				DEFVAL { 2 }
				InDB = NO
				TypeInDB=UCHAR
				ELBIT_PERM(0x00000003)
				ADMIN_PERM(0x00000003)
				TECH_PERM(0x00000003)
				USER_PERM(0x00000003)"
			::= { moduleAHud 4 }

		pll4PowerEnable OBJECT-TYPE
			SYNTAX TypePllPowerEnable
			MAX-ACCESS read-write
			STATUS current
			DESCRIPTION
				"Select PLL power Enable.
				DEFVAL { 2 }
				InDB = NO
				TypeInDB=UCHAR
				ELBIT_PERM(0x00000003)
				ADMIN_PERM(0x00000003)
				TECH_PERM(0x00000003)
				USER_PERM(0x00000003)"
			::= { moduleAHud 5 }
		
		lnaByPass OBJECT-TYPE
			SYNTAX TypeLnaByPassEnable
			MAX-ACCESS read-write
			STATUS current
			DESCRIPTION
				"Select LAN By Pass Enable.
				DEFVAL { 2 }
				InDB = NO
				TypeInDB=UCHAR
				ELBIT_PERM(0x00000003)
				ADMIN_PERM(0x00000003)
				TECH_PERM(0x00000003)
				USER_PERM(0x00000003)"
			::= { moduleAHud 6 }
		
		loopbackEnable OBJECT-TYPE
			SYNTAX TypeLoopbackEnable
			MAX-ACCESS read-write
			STATUS current
			DESCRIPTION
				"LoopBack Enable.
				DEFVAL { 2 }
				InDB = NO
				TypeInDB=UCHAR
				ELBIT_PERM(0x00000003)
				ADMIN_PERM(0x00000003)
				TECH_PERM(0x00000003)
				USER_PERM(0x00000003)"
			::= { moduleAHud 7 }

		outPutRssi OBJECT-TYPE
			SYNTAX TypeRssiOnOff
			MAX-ACCESS read-write
			STATUS current
			DESCRIPTION
				"OutPut Rssi.
				DEFVAL { 2 }
				InDB = NO
				TypeInDB=UCHAR
				ELBIT_PERM(0x00000003)
				ADMIN_PERM(0x00000003)
				TECH_PERM(0x00000003)
				USER_PERM(0x00000003)"
			::= { moduleAHud 8 }
		
		inPutRssi OBJECT-TYPE
			SYNTAX TypeRssiOnOff
			MAX-ACCESS read-write
			STATUS current
			DESCRIPTION
				"Input rssi.
				DEFVAL { 2 }
				InDB = NO
				TypeInDB=UCHAR
				ELBIT_PERM(0x00000003)
				ADMIN_PERM(0x00000003)
				TECH_PERM(0x00000003)
				USER_PERM(0x00000003)"
			::= { moduleAHud 9 }

		sawFilterSelet OBJECT-TYPE
			SYNTAX TypeSawFilterSelect
			MAX-ACCESS read-write
			STATUS current
			DESCRIPTION
				"Select Receive Saw Filter
				DEFVAL { 2 }
				InDB = NO
				TypeInDB=UCHAR
				ELBIT_PERM(0x00000003)
				ADMIN_PERM(0x00000003)
				TECH_PERM(0x00000003)
				USER_PERM(0x00000003)"
			::= { moduleAHud 10 }

		txRMSDetector OBJECT-TYPE
			SYNTAX TypeTxRmsDetector
			MAX-ACCESS read-write
			STATUS current
			DESCRIPTION
				"Tx RMS Detector
				DEFVAL { 2 }
				InDB = NO
				TypeInDB=UCHAR
				ELBIT_PERM(0x00000003)
				ADMIN_PERM(0x00000003)
				TECH_PERM(0x00000003)
				USER_PERM(0x00000003)"
			::= { moduleAHud 11 }

		loTxLanaSelect OBJECT-TYPE
			SYNTAX TypeTxRmsDetector
			MAX-ACCESS read-write
			STATUS current
			DESCRIPTION
				"Lo TX LANA SELECT
				DEFVAL { 2 }
				InDB = NO
				TypeInDB=UCHAR
				ELBIT_PERM(0x00000003)
				ADMIN_PERM(0x00000003)
				TECH_PERM(0x00000003)
				USER_PERM(0x00000003)"
			::= { moduleAHud 12 }

		loRxLanaSelect OBJECT-TYPE
			SYNTAX TypeTxRmsDetector
			MAX-ACCESS read-write
			STATUS current
			DESCRIPTION
				"Lo RX LANA SELECT
				DEFVAL { 2 }
				InDB = NO
				TypeInDB=UCHAR
				ELBIT_PERM(0x00000003)
				ADMIN_PERM(0x00000003)
				TECH_PERM(0x00000003)
				USER_PERM(0x00000003)"
			::= { moduleAHud 13 }

		upLinkPOwerControl OBJECT-TYPE
			SYNTAX TypePllPowerEnable
			MAX-ACCESS read-write
			STATUS current
			DESCRIPTION
				"UpLink Power Control
				DEFVAL { 2 }
				InDB = NO
				TypeInDB=UCHAR
				ELBIT_PERM(0x00000003)
				ADMIN_PERM(0x00000003)
				TECH_PERM(0x00000003)
				USER_PERM(0x00000003)"
			::= { moduleAHud 14 }

		downLinkPOwerControl OBJECT-TYPE
			SYNTAX TypePllPowerEnable
			MAX-ACCESS read-write
			STATUS current
			DESCRIPTION
				"DownLink Power Control
				DEFVAL { 2 }
				InDB = NO
				TypeInDB=UCHAR
				ELBIT_PERM(0x00000003)
				ADMIN_PERM(0x00000003)
				TECH_PERM(0x00000003)
				USER_PERM(0x00000003)"
			::= { moduleAHud 15 }

		epromWriteProtct OBJECT-TYPE
			SYNTAX TypeEpromWriteProtect
			MAX-ACCESS read-write
			STATUS current
			DESCRIPTION
				"Eprotm Write Protect
				DEFVAL { 2 }
				InDB = NO
				TypeInDB=UCHAR
				ELBIT_PERM(0x00000003)
				ADMIN_PERM(0x00000003)
				TECH_PERM(0x00000003)
				USER_PERM(0x00000003)"
			::= { moduleAHud 16 }   
			
			
			networkProcessor OBJECT IDENTIFIER ::={odu 30}
             
              gloabalParameters OBJECT IDENTIFIER ::={networkProcessor 1} 
              
                   portConfig OBJECT IDENTIFIER ::={gloabalParameters 1} 
                   
                       controlBits OBJECT IDENTIFIER ::={portConfig 1}            
                       	validBit OBJECT-TYPE
						SYNTAX Integer32 (0..1)
						MAX-ACCESS read-write
						STATUS current
						DESCRIPTION      
						"Valid bit (always 1)"
					::= { controlBits 1}               
              
                       	portEnabled OBJECT-TYPE
						SYNTAX Integer32 (0..1)
						MAX-ACCESS read-write
						STATUS current
						DESCRIPTION      
						"Port enabled (1 - enable, 0 - disable)"
					::= { controlBits 2}  
              
                       	learningEnabled OBJECT-TYPE
						SYNTAX Integer32 (0..1)
						MAX-ACCESS read-write
						STATUS current
						DESCRIPTION      
						"Learning enabled on port (1 - enable, 0 - disable)"
					::= { controlBits 3}             
                                            
                       	egressVLANModify OBJECT-TYPE
						SYNTAX Integer32 (0..1)
						MAX-ACCESS read-write
						STATUS current
						DESCRIPTION      
						"Egress VLAN Modify  (1 - enable, 0 - disable)"
					::= { controlBits 4}                                           
                                            
                       	qoSEnabled OBJECT-TYPE
						SYNTAX Integer32 (0..1)
						MAX-ACCESS read-write
						STATUS current
						DESCRIPTION      
						"QOS enabled on port (1 - enable, 0 - disable)"
					::= { controlBits 5}     
					
                       	sourceMACaddressCheck OBJECT-TYPE
						SYNTAX Integer32 (0..1)
						MAX-ACCESS read-write
						STATUS current
						DESCRIPTION      
						"Source MAC address checking enabled
							0 - don't check MAC enable feature, 1 - check "
					::= { controlBits 6} 					
					
                       	vlanAwareness OBJECT-TYPE
						SYNTAX Integer32 (0..1)
						MAX-ACCESS read-write
						STATUS current
						DESCRIPTION      
						"VLAN awareness
						0 - use default VLAN, 1 - use VLAN from packet"
					::= { controlBits 7} 
					
                       	cpuLearning OBJECT-TYPE
						SYNTAX Integer32 (0..1)
						MAX-ACCESS read-write
						STATUS current
						DESCRIPTION      
						"CPU Learning
							0 - disable, 1 - only CPU can learn"
					::= { controlBits 8} 
					
                       	defaultBypassMode OBJECT-TYPE
						SYNTAX Integer32 (0..1)
						MAX-ACCESS read-write
						STATUS current
						DESCRIPTION      
						"0 - disable, 1 - bypass mode active (look at Bypass Output port)"
					::= { controlBits 9}										
					                             
			
					defaultVlanID OBJECT-TYPE
					SYNTAX Integer32 (0..4095)
					MAX-ACCESS read-write
					STATUS current
					DESCRIPTION      
					"12 bits relevant "
					::= { portConfig 2}										
					                     					
					logicalPortID OBJECT-TYPE
					SYNTAX Integer32 
					MAX-ACCESS read-write
					STATUS current
					DESCRIPTION      
					"4 bits relevant"
					::= { portConfig 3}						
														
					defaultPriority OBJECT-TYPE
					SYNTAX Integer32(0..15) 
					MAX-ACCESS read-write
					STATUS current
					DESCRIPTION      
					"4 bits relevant"
					::= { portConfig 4}						
					
					
					reserved OBJECT-TYPE
					SYNTAX Integer32(0..15) 
					MAX-ACCESS read-write
					STATUS current
					DESCRIPTION      
					"TBD"
					::= { portConfig 5}
					
					reservedForHW OBJECT-TYPE
					SYNTAX Integer32(0..255) 
					MAX-ACCESS read-write
					STATUS current
					DESCRIPTION      
					"Bit 63 - Frame type, bits 62:61 - decode offset"
					::= { portConfig 6}	
										
					myMAC OBJECT-TYPE
					SYNTAX OCTET STRING (SIZE (0..255))
					MAX-ACCESS read-write
					STATUS current
					DESCRIPTION      
					"Bit 63 - Frame type, bits 62:61 - decode offset"
					::= { portConfig 7}						
					
					bypassOutputPort OBJECT-TYPE
					SYNTAX Integer32(0..255)
					MAX-ACCESS read-write
					STATUS current
					DESCRIPTION      
					"Out port for bypass"
					::= { portConfig 8}						
                              
                	globalGoodToGo OBJECT-TYPE
					SYNTAX Integer32(0..1)
					MAX-ACCESS read-write
					STATUS current
					DESCRIPTION      
					"Out port for bypass"
					::= { gloabalParameters 2}	              
                              
                   	linkNumber OBJECT-TYPE
					SYNTAX Integer32(1..3)
					MAX-ACCESS read-write
					STATUS current
					DESCRIPTION      
					"Out port for bypass"
					::= { networkProcessor 2}
					                           

			 npLinkConfig OBJECT IDENTIFIER ::={networkProcessor 3} 
			        vlanTable OBJECT IDENTIFIER ::={npLinkConfig 1}                               
			                                      
			  			vlanID OBJECT-TYPE
						SYNTAX Integer32(0..4095)
						MAX-ACCESS read-write
						STATUS current
						DESCRIPTION      
						"12 bits relevant, rest must be 0"
						::= { vlanTable 1}
					
						vlanTableResults OBJECT IDENTIFIER ::={vlanTable 2}     
					        vlanTableControls OBJECT IDENTIFIER ::={vlanTableResults 1}  
					            validVlanBit 	OBJECT-TYPE
								SYNTAX Integer32(0..1)
								MAX-ACCESS read-write
								STATUS current
								DESCRIPTION      
								"Bit 0 - Valid"	
								::= { vlanTableControls 1}
								
							    vlanMatch 	OBJECT-TYPE
								SYNTAX Integer32(0..1)
								MAX-ACCESS read-write
								STATUS current
								DESCRIPTION      
								"Bit 1 - Match"	
								::= { vlanTableControls 2}          
					
							portBitmap OBJECT-TYPE
							SYNTAX Integer32(0..65535)
							MAX-ACCESS read-write
							STATUS current
							DESCRIPTION      
							""	
							::= { vlanTableResults 2} 

							tmFlowIDOffset OBJECT-TYPE
							SYNTAX Integer32(0..65535)
							MAX-ACCESS read-write
							STATUS current
							DESCRIPTION      
							"Elbit case - always zero"	
							::= { vlanTableResults 3} 
							
							vlanTableGoodToGo OBJECT-TYPE
							SYNTAX Integer32(0..1)
							MAX-ACCESS read-write
							STATUS current
							DESCRIPTION      
							"Elbit case - always zero"	
							::= { vlanTable 3} 
														
							
						macTable OBJECT IDENTIFIER ::={npLinkConfig 2}
						
		                macAddr OBJECT-TYPE
						SYNTAX OCTET STRING (SIZE (0..255))
						MAX-ACCESS read-write
						STATUS current
						DESCRIPTION      
						""
						::= { macTable 1} 
						
			  			vlanKey OBJECT-TYPE
						SYNTAX Integer32(0..65535)
						MAX-ACCESS read-write
						STATUS current
						DESCRIPTION      
						"12 bits relevant, rest must be 0"
						::= { macTable 2}
						
												
					macTableResults OBJECT IDENTIFIER ::={macTable 3} 
					
	                   controls OBJECT IDENTIFIER ::={macTableResults 1} 
	                    
	                    valid OBJECT-TYPE
						SYNTAX Integer32 (0..1)
						MAX-ACCESS read-write
						STATUS current
						DESCRIPTION      
						"Bit 0 - Valid"
						::= { controls 1}
						
	                    match OBJECT-TYPE
						SYNTAX Integer32 (0..1)
						MAX-ACCESS read-write
						STATUS current
						DESCRIPTION      
						"Bit 1 - Match"
						::= { controls 2}
						
	                    distrustedAddress OBJECT-TYPE
						SYNTAX Integer32 (0..1)
						MAX-ACCESS read-write
						STATUS current
						DESCRIPTION      
						"Bit 2 - Distrusted MAC address ( 1 - distrusted address, 0 - not distrusted)"
						::= { controls 3}						
												
	                    staticEntry OBJECT-TYPE
						SYNTAX Integer32 (0..1)
						MAX-ACCESS read-write
						STATUS current
						DESCRIPTION      
						"Bit 3 - Static entry  (1 - static entry, 0 - not static)"
						::= { controls 4}
						
					macOutputLogicalPortID OBJECT-TYPE
					SYNTAX Integer32 (0..255)
					MAX-ACCESS read-write
					STATUS current
					DESCRIPTION      
					""
					::= { macTableResults 2}
																	
					compressedMACID OBJECT-TYPE
					SYNTAX Integer32 (0..65535)
					MAX-ACCESS read-write
					STATUS current
					DESCRIPTION      
					""
					::= { macTableResults 3}
											
					macReserved OBJECT-TYPE
					SYNTAX Integer32
					MAX-ACCESS read-write
					STATUS current
					DESCRIPTION      
					""
					::= { macTableResults 4}
					
					macTableGoodToGo OBJECT-TYPE
					SYNTAX Integer32 (0..1)
					MAX-ACCESS read-write
					STATUS current
					DESCRIPTION      
					""
					::= { macTable 4}

					
					
				 internalTCAM OBJECT IDENTIFIER ::={npLinkConfig 3}  
				 
					 internalTCAMresult OBJECT IDENTIFIER ::={internalTCAM 1} 
					    internalControls OBJECT IDENTIFIER ::={internalTCAMresult 1} 
					    
                        internalValid OBJECT-TYPE
						SYNTAX Integer32 (0..1)
						MAX-ACCESS read-write
						STATUS current
						DESCRIPTION      
						"Bit 0 - Valid"
						::= { internalControls 1}

                        matchOnTable OBJECT-TYPE
						SYNTAX Integer32 (0..1)
						MAX-ACCESS read-write
						STATUS current
						DESCRIPTION      
						"Bit 6 - Match on table "
						::= { internalControls 2}
						
                    rankID OBJECT-TYPE
					SYNTAX Integer32 
					MAX-ACCESS read-write
					STATUS current
					DESCRIPTION      
					"The result line of the TCAM"
					::= { internalTCAMresult 2}  

				 	internalLogicalPortID OBJECT-TYPE
					SYNTAX Integer32
					MAX-ACCESS read-write
					STATUS current
					DESCRIPTION      
					"4 bits relevant"
					::= { internalTCAM 2}
			
		          	vlanAndPriority OBJECT-TYPE
					SYNTAX Integer32 (0..65535)
					MAX-ACCESS read-write
					STATUS current
					DESCRIPTION      
					""
					::= { internalTCAM 3}

		          	ipTOS OBJECT-TYPE
					SYNTAX Integer32 (0..255)
					MAX-ACCESS read-write
					STATUS current
					DESCRIPTION      
					""
					::= { internalTCAM 4}
		
		          	sourceIP OBJECT-TYPE
					SYNTAX OCTET STRING (SIZE (0..255))
					MAX-ACCESS read-write
					STATUS current
					DESCRIPTION      
					""
					::= { internalTCAM 5}
		
		
		          	destinationIP OBJECT-TYPE
					SYNTAX OCTET STRING (SIZE (0..255))
					MAX-ACCESS read-write
					STATUS current
					DESCRIPTION      
					""
					::= { internalTCAM 6}
					
			       	compressedDA OBJECT-TYPE
					SYNTAX Integer32 (0..65535)
					MAX-ACCESS read-write
					STATUS current
					DESCRIPTION      
					"Obtained from MAC table. Value 0 indicates no match or learned MAC."
					::= { internalTCAM 7}
					
			       	compressedSA OBJECT-TYPE
					SYNTAX Integer32 (0..65535)
					MAX-ACCESS read-write
					STATUS current
					DESCRIPTION      
					"Obtained from MAC table. Value 0 indicates no match or learned MAC."
					::= { internalTCAM 8}
					
			       	reservedTCAM OBJECT-TYPE
					SYNTAX Integer32 (0..65535)
					MAX-ACCESS read-write
					STATUS current
					DESCRIPTION      
					""
					::= { internalTCAM 9}
					
			       	internalTableGoodToGo OBJECT-TYPE
					SYNTAX Integer32 (0..1)
					MAX-ACCESS read-write
					STATUS current
					DESCRIPTION      
					""
					::= { internalTCAM 10}
							
																
		         priorityTable OBJECT IDENTIFIER ::={npLinkConfig 4}
		         
		            tcamRankID OBJECT-TYPE
					SYNTAX Integer32 (0..65535)
					MAX-ACCESS read-write
					STATUS current
					DESCRIPTION      
					""
					::= { priorityTable 1}
					
					
		          priorityTableResult OBJECT IDENTIFIER ::={priorityTable 2}
                     priorityControls OBJECT IDENTIFIER ::={priorityTableResult 1}
                     
                        priorityValid OBJECT-TYPE
						SYNTAX Integer32 (0..1)
						MAX-ACCESS read-write
						STATUS current
						DESCRIPTION      
						"Bit 0 - Valid"
						::= { priorityControls 1}

                        priorityMatch OBJECT-TYPE
						SYNTAX Integer32 (0..1)
						MAX-ACCESS read-write
						STATUS current
						DESCRIPTION      
						"Bit 1 - Match"
						::= { priorityControls 2}
		
		                useTB OBJECT-TYPE
						SYNTAX Integer32 (0..1)
						MAX-ACCESS read-write
						STATUS current
						DESCRIPTION      
						"Bit 2 - use TB ( 1 - check TB, 0 - don't check)"
						::= { priorityControls 3} 
						
		                useTBflooding OBJECT-TYPE
						SYNTAX Integer32 (0..1)
						MAX-ACCESS read-write
						STATUS current
						DESCRIPTION      
						"Bit 3 - use TB flooding ( 1 - check flooding TB, 0 - don't check)"
						::= { priorityControls 4}
						
		                dropBit OBJECT-TYPE
						SYNTAX Integer32 (0..1)
						MAX-ACCESS read-write
						STATUS current
						DESCRIPTION      
						"Bit 4 - Drop Bit (1 - drop this packet, 0 - don't drop)"
						::= { priorityControls 5}
						 						
		
		            priorityNumber OBJECT-TYPE
					SYNTAX INTEGER(0..255)
					MAX-ACCESS read-write
					STATUS current
					DESCRIPTION      
					"Use values 0-3, 64-67 (highest priority 0)"
					::= { priorityTableResult 2}

		            priorityForFlooding OBJECT-TYPE
					SYNTAX INTEGER(0..255)
					MAX-ACCESS read-write
					STATUS current
					DESCRIPTION      
					"Use values 0-3, 64-67 (highest priority 0)"
					::= { priorityTableResult 3}

		            tbIndex OBJECT-TYPE
					SYNTAX INTEGER(0..65535)
					MAX-ACCESS read-write
					STATUS current
					DESCRIPTION      
					""
					::= { priorityTableResult 4}		
		
		            floodingTBIndex OBJECT-TYPE
					SYNTAX INTEGER(0..65535)
					MAX-ACCESS read-write
					STATUS current
					DESCRIPTION      
					""
					::= { priorityTableResult 5}		
		
			 
		            priorityReserved OBJECT-TYPE
					SYNTAX INTEGER
					MAX-ACCESS read-write
					STATUS current
					DESCRIPTION      
					""
					::= { priorityTableResult 6}			 

		            priorityTableGoodToGo OBJECT-TYPE
					SYNTAX INTEGER (0..1)
					MAX-ACCESS read-write
					STATUS current
					DESCRIPTION      
					""
					::= { priorityTable 3}			 
			 
			 
			        routingTable OBJECT IDENTIFIER ::={npLinkConfig 5}
			        
			        routingIPaddress OBJECT-TYPE
					SYNTAX OCTET STRING (SIZE (0..255))
					MAX-ACCESS read-write
					STATUS current
					DESCRIPTION      
					""
					::= { routingTable 1}
					
					routingControls OBJECT IDENTIFIER ::={routingTable 2} 
					
                        routingValid OBJECT-TYPE
						SYNTAX Integer32 (0..1)
						MAX-ACCESS read-write
						STATUS current
						DESCRIPTION      
						"Bit 0 - Valid"
						::= { routingControls 1}

                        routingMatch OBJECT-TYPE
						SYNTAX Integer32 (0..1)
						MAX-ACCESS read-write
						STATUS current
						DESCRIPTION      
						"Bit 1 - Match"
						::= { routingControls 2}

                        addVLANtag OBJECT-TYPE
						SYNTAX Integer32 (0..1)
						MAX-ACCESS read-write
						STATUS current
						DESCRIPTION      
						"Bit 2  -  1 - add VLAN tag , 0 - don't add"
						::= { routingControls 3}
					
                        removeVLANtag OBJECT-TYPE
						SYNTAX Integer32 (0..1)
						MAX-ACCESS read-write
						STATUS current
						DESCRIPTION      
						"Bit 3 -  1 remove VLAN tag, 0 - don't remove "
						::= { routingControls 4}

                        updateVLANtag OBJECT-TYPE
						SYNTAX Integer32 (0..1)
						MAX-ACCESS read-write
						STATUS current
						DESCRIPTION      
						"Bits 2&3 set - update (remove and add) VLAN tag "
						::= { routingControls 5}
			 
			 
		            routingOutputLogicalPortID OBJECT-TYPE
					SYNTAX INTEGER(0..255)
					MAX-ACCESS read-write
					STATUS current
					DESCRIPTION      
					""
					::= { routingTable 3}
			 
		            vlanTAG OBJECT-TYPE
					SYNTAX INTEGER(0..65535)
					MAX-ACCESS read-write
					STATUS current
					DESCRIPTION      
					""
					::= { routingTable 4}			 
			 
		            destinationMAC OBJECT-TYPE
					SYNTAX OCTET STRING (SIZE (0..255))
					MAX-ACCESS read-write
					STATUS current
					DESCRIPTION      
					""
					::= { routingTable 5}			 
			 
			        routingReserved OBJECT-TYPE
					SYNTAX INTEGER
					MAX-ACCESS read-write
					STATUS current
					DESCRIPTION      
					""
					::= { routingTable 6}
			         routingTableGoodToGo OBJECT-TYPE
					SYNTAX INTEGER (0..1)
					MAX-ACCESS read-write
					STATUS current
					DESCRIPTION      
					""
					::= { routingTable 7}

			 
			  			   
				    outputPortTable OBJECT IDENTIFIER ::={npLinkConfig 6}
			        
			        outputLogicalPortID OBJECT-TYPE
					SYNTAX OCTET STRING (SIZE (0..255))
					MAX-ACCESS read-write
					STATUS current
					DESCRIPTION      
					"16 ports."
					::= { outputPortTable 1}
					
					outputPortControls OBJECT IDENTIFIER ::={outputPortTable 2}
                        outputValid OBJECT-TYPE
						SYNTAX Integer32 (0..1)
						MAX-ACCESS read-write
						STATUS current
						DESCRIPTION      
						"Bit 0 - Valid"
						::= { outputPortControls 1}

                        outputmatch OBJECT-TYPE
						SYNTAX Integer32 (0..1)
						MAX-ACCESS read-write
						STATUS current
						DESCRIPTION      
						"Bit 1 - Match"
						::= { outputPortControls 2}

                        portEnable OBJECT-TYPE
						SYNTAX Integer32 (0..1)
						MAX-ACCESS read-write
						STATUS current
						DESCRIPTION      
						"Bit 2 - Port enable (0-disable, 1-enable)"
						::= { outputPortControls 3}
					
			 	 
		            tmFlowIDbase OBJECT-TYPE
					SYNTAX OCTET STRING (SIZE (0..255))
					MAX-ACCESS read-write
					STATUS current
					DESCRIPTION      
					""
					::= { outputPortTable 3}
			 
		            sourceMACaddr OBJECT-TYPE
					SYNTAX OCTET STRING (SIZE (0..255))
					MAX-ACCESS read-write
					STATUS current
					DESCRIPTION      
					""
					::= { outputPortTable 4}			 
			 
		            outputDestinationMAC OBJECT-TYPE
					SYNTAX OCTET STRING (SIZE (0..255))
					MAX-ACCESS read-write
					STATUS current
					DESCRIPTION      
					"For routing treatment"
					::= { outputPortTable 5}			 
			 
			        outputPortReserved OBJECT-TYPE
					SYNTAX INTEGER
					MAX-ACCESS read-write
					STATUS current
					DESCRIPTION      
					""
					::= { outputPortTable 6}
		   
			   
			        outputPortGoodToGo OBJECT-TYPE
					SYNTAX INTEGER(0..1)
					MAX-ACCESS read-write
					STATUS current
					DESCRIPTION      
					""
					::= { outputPortTable 7}
					
		afikKeys OBJECT IDENTIFIER ::={odu 31}  
		
			loadKeyToBank OBJECT-TYPE
			SYNTAX TypeEnableBank
			MAX-ACCESS read-write
			STATUS current
			DESCRIPTION      
			"points to which bank the key will be loaded"
			::= { afikKeys 1}
		
			activeBank OBJECT-TYPE
			SYNTAX TypeBank
			MAX-ACCESS read-write
			STATUS current
			DESCRIPTION      
			"get or set currnet active bank"
			::= { afikKeys 2} 
			
			requestInfoFromBankNumber OBJECT-TYPE
			SYNTAX TypeBank
			MAX-ACCESS read-write
			STATUS current
			DESCRIPTION      
			"set the keys bank number from which
			 the data will be collected"
			::= { afikKeys 3} 
			
			requestInfoOfKeyType OBJECT-TYPE
			SYNTAX TypeKey
			MAX-ACCESS read-write
			STATUS current
			DESCRIPTION      
			"set the key type of which
			 the data will be colllected"
			::= { afikKeys 4} 
			            
           	getSetupDate OBJECT-TYPE
            SYNTAX OCTET STRING (SIZE (0..255))
           	MAX-ACCESS read-only
           	STATUS current
			DESCRIPTION
            "get setup date of the key which 
            bankNumber and keyType leaves points to"
            ::= { afikKeys 5}
            
            
           	getExpirationDate OBJECT-TYPE
            SYNTAX OCTET STRING (SIZE (0..255))
           	MAX-ACCESS read-only
           	STATUS current
			DESCRIPTION
            "get expiration date of the key which
            bankNumber and keyType leaves points to"
            ::= { afikKeys 6}
            
           	getKeyName OBJECT-TYPE
            SYNTAX OCTET STRING (SIZE (0..255))
           	MAX-ACCESS read-only
           	STATUS current
			DESCRIPTION
            "get the name of the key which 
            bankNumber and keyType leaves points to"
            ::= { afikKeys 7}	

			isKeyExist OBJECT-TYPE
            SYNTAX BoolType
           	MAX-ACCESS read-only
           	STATUS current
			DESCRIPTION
            "is key exist according to a requestInfoOfKeyType
			 and requestInfoFromBankNumber leafs"
            ::= { afikKeys 8}
			
			deleteBank OBJECT-TYPE
            SYNTAX DelKeyType
           	MAX-ACCESS read-write
           	STATUS current
			DESCRIPTION
            "Deletes whole bank"
            ::= { afikKeys 9}			
	END
--
-- ELBIT-GLOBAL-REG-V2.mib
--
